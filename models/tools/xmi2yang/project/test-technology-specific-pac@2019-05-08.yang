module test-technology-specific-pac {
    namespace "urn:onf:yang:test-technology-specific-pac";
    prefix test-technology-specific-pac;
    import test-core-model {
        prefix test-core-model;
    }
    organization "OpenNetworkingFoundation (ONF)";
    contact "ONF";
    description "none";
    revision 2019-05-08 {
        description "Test project to check UML-to-YANG tool.";
        reference "ONF-TR-512, ONF-TR-532, ONF-TR-541, ONF-TR-545, RFC 6020 and RFC 6087";
    }
    augment "/test-core-model:test-control-construct/test-core-model:test-logical-termination-point/test-core-model:test-layer-protocol"{
        uses technology-specific-lp-spec;
        description "none";
    }
    /****************************************
    * grouping statements for object classes
    **************************************/ 
        grouping technology-specific-pac {
            leaf technology-specific-attribute {
                type string;
                description "none";
            }
            container test-capability {
                config false;
                uses test-capability-ref;
                description "none";
            }
            container test-configuration {
                uses test-configuration-ref;
                description "none";
            }
            container test-status {
                config false;
                uses test-status-ref;
                description "none";
            }
            description "none";
        }

    /****************************************
    * package diagrams
    **************************************/ 
        grouping technology-specific-lp-spec {
            container technology-specific-pac {
                uses technology-specific-pac;
                description "none";
            }
            description "none";
        }

    grouping test-capability-ref {
        leaf capability-1 {
            type string;
            description "none";
        }
        leaf capability-2 {
            type string;
            description "none";
        }
        description "none";
    }
    grouping test-configuration-ref {
        leaf configuration-1 {
            type string;
            description "none";
        }
        leaf configuration-2 {
            type string;
            description "none";
        }
        description "none";
    }
    grouping test-status-ref {
        leaf status-1 {
            type string;
            config false;
            description "none";
        }
        leaf status-2 {
            type string;
            config false;
            description "none";
        }
        leaf signed-integer-32 {
            type int32 {
            }
            units "dbm/10";
            default -99;
            description "Expected type int32 with unit dbm/10 and default -99.";
        }
        leaf unsinged-integer-8 {
            type uint8 {
            }
            units "kbit/s";
            description "Expected type uin8 with unit kbit/s.";
        }
        leaf unsigned-integer-64 {
            type uint64 {
                range "1..max";
            }
            units "s";
            description "Expected type uin64 with unit s and value range 1...max.";
        }
        description "none";
    }
}
