module MicrowaveModel-TypeDefinitions {
    namespace "uri:onf:MicrowaveModel-TypeDefinitions";
    prefix MicrowaveModel-TypeDefinitions;

    import CoreModel-CoreFoundationModule-SuperClassesAndCommonPackages {
        prefix CoreModel-CoreFoundationModule-SuperClassesAndCommonPackages;
    }
    import MicrowaveModel-ObjectClasses-SuperClasses {
        prefix MicrowaveModel-ObjectClasses-SuperClasses;
    }
    import G_874_1_model-Object_Classes {
        prefix G_874_1_model-Object_Classes;
    }
    import CoreModel-CoreFoundationModule-StateModel {
        prefix CoreModel-CoreFoundationModule-StateModel;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-09-13 {
        description 
            "Initial revision."; 
        reference 
            "ONF TR 532: A YANG Data Model for Microwave Transport Networks."; 
    }

    typedef severityType {
        description "According to ITU-T M.3160";
        type enumeration {
            enum non-alarmed;
            enum warning;
            enum minor;
            enum major;
            enum critical;
        }
    }
    grouping channelPlanType {
        leaf supportedChannelPlan {
            type string;
            config false;
            description "Unique name (e.g. CEPT/ERC/REC (01) 04 Annex 5) of an international agreement that describe allocations of frequency channels, to which this air interface complies. Corresponding channel plans to be delivered by the hardware vendor and to be stored by the operator in the controller/application attached database.";
        }
        leaf duplexDistanceIsVariable {
            type boolean;
            config false;
            description "To be set on  'true', if the distance between transmitted and received frequency is variable.";
            default false;
        }
        leaf duplexDistance {
            type int32;
            config false;
            description "Distance between transmitted and received frequency.";
            units "kHz";
            default -1;
        }
        leaf autoFreqSelectIsAvail {
            type boolean;
            config false;
            description "In case the microwave radio is capable of automatically selecting the transmit frequency in unlicensed bands, this field shall contain a 'true'.";
            default false;
        }
        list transmissionModeList {
            key 'transmissionModeId';
            ordered-by system;
            uses transmissionModeType;
            min-elements 1;
        }
    }
    grouping transmissionModeType {
        leaf transmissionModeId {
            type CoreModel-CoreFoundationModule-SuperClassesAndCommonPackages:UniversalId;
            config false;
            description "Indentifies the transmissionMode for internal reference.";
        }
        leaf channelBandwidth {
            type int32;
            config false;
            description "Bandwidth of the transmit channel. The value shall be expressed explicitly (means in kHz) not as a reference to an international agreement. The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;";
            units "kHz";
            default -1;
        }
        leaf modulationScheme {
            type int16;
            config false;
            description "Modulation scheme, which is base to the other characteristics described in the same transmissionModeType data type. The modulation scheme shall be described by the number of symbols (e.g. BPSK->'2' or 256QAM->'256').";
            units "symbols";
            default -1;
        }
        leaf informationRate {
            type int8;
            config false;
            description "Information rate of the coding scheme in %.";
            units "%";
            default -1;
        }
        leaf txPowerMin {
            type int8;
            config false;
            description "Value of the minimum transmit power the modem can operate in dBm.";
            units "dBm";
            default 99;
        }
        leaf txPowerMax {
            type int8;
            config false;
            description "Value of the maximum transmit power the modem can operate in dBm.";
            units "dBm";
            default 99;
        }
        leaf rxThreshold {
            type int16;
            config false;
            description "Value of the receive level required to decode the received signal with a Bit Error Rate of 1e-6 or less.";
            units "dBm";
            default 99;
        }
        leaf amUpshiftLevel {
            type int8;
            config false;
            description "Value of the receive level that has to be exceeded to shift into a higher modulation scheme.";
            units "dBm";
            default 99;
        }
        leaf amDownshiftLevel {
            type int8;
            config false;
            description "Value of the receive level that has to be exceeded for not shifting into a lower modulation scheme.";
            units "dBm";
            default 99;
        }
        leaf xpicIsAvail {
            type boolean;
            config false;
            description "In case the Air Interface Port is capable of XPIC, this field shall contain a 'true'.";
            default false;
        }
    }
    typedef polarizationType {
        type enumeration {
            enum not-specified;
            enum horizontal;
            enum vertical;
        }
    }
    grouping airInterfaceProblemSeverityType {
        leaf problemKindName {
            type string;
            description "Name of the alarm according to AirInterface::AirInterfaceCapability::supportedAlarms";
        }
        leaf problemKindSeverity {
            type severityType;
            description "Severity of this type of alarm.";
            default "warning";
        }
    }
    grouping airInterfaceCurrentProblemType {
        uses MicrowaveModel-ObjectClasses-SuperClasses:MwCurrentProblem;
        leaf problemName {
            type string;
            config false;
            description "Name of the alarm according to AirInterface::AirInterfaceCapability::supportedAlarms";
            default "Air interface problems not yet defined.";
        }
        leaf problemSeverity {
            type severityType;
            config false;
            description "Severity of the alarm.";
            default "warning";
        }
    }
    grouping airInterfacePerformanceType {
        description "Consolidated performance information of the air interface.";
        leaf es {
            type int32;
            config false;
            description "Number of errored seconds.";
            units "s";
            default -1;
        }
        leaf ses {
            type int32;
            config false;
            description "Number of severely errored seconds.";
            units "s";
            default -1;
        }
        leaf cses {
            type int32;
            config false;
            description "Number of consecutive severely errored seconds.";
            units "s";
            default -1;
        }
        leaf unavailability {
            type int32;
            config false;
            description "Total time of unavailability in seconds.";
            units "s";
            default -1;
        }
        leaf txLevelMin {
            type int8;
            config false;
            description "Minimum transmit power. Signed integers are required.";
            units "dBm";
            default 99;
        }
        leaf txLevelMax {
            type int8;
            config false;
            description "Maximum transmit power. Signed integers are required.";
            units "dBm";
            default 99;
        }
        leaf txLevelAvg {
            type int8;
            config false;
            description "Averaged transmit power. Signed integers are required.";
            units "dBm";
            default 99;
        }
        leaf rxLevelMin {
            type int8;
            config false;
            description "Minimum receive level. Signed integers are required.";
            units "dBm";
            default 99;
        }
        leaf rxLevelMax {
            type int8;
            config false;
            description "Maximum receive level. Signed integers are required.";
            units "dBm";
            default 99;
        }
        leaf rxLevelAvg {
            type int8;
            config false;
            description "Averaged receive level. Signed integers are required.";
            units "dBm";
            default 99;
        }
        leaf time2Symbols {
            type int32;
            config false;
            units "s";
            default -1;
        }
        leaf time4SymbolsS {
            type int32;
            config false;
            description "Sum of all seconds the transmitter operated in e.g. 4QAM strong.";
            units "s";
            default -1;
        }
        leaf time4Symbols {
            type int32;
            config false;
            units "s";
            default -1;
        }
        leaf time8Symbols {
            type int32;
            config false;
            units "s";
            default -1;
        }
        leaf time16SymbolsS {
            type int32;
            config false;
            units "s";
            default -1;
        }
        leaf time16Symbols {
            type int32;
            config false;
            units "s";
            default -1;
        }
        leaf time32Symbols {
            type int32;
            config false;
            units "s";
            default -1;
        }
        leaf time64Symbols {
            type int32;
            config false;
            units "s";
            default -1;
        }
        leaf time128Symbols {
            type int32;
            config false;
            units "s";
            default -1;
        }
        leaf time256Symbols {
            type int32;
            config false;
            units "s";
            default -1;
        }
        leaf time512Symbols {
            type int32;
            config false;
            units "s";
            default -1;
        }
        leaf time512SymbolsL {
            type int32;
            config false;
            units "s";
            default -1;
        }
        leaf time1024Symbols {
            type int32;
            config false;
            units "s";
            default -1;
        }
        leaf time1024SymbolsL {
            type int32;
            config false;
            units "s";
            default -1;
        }
        leaf time2048Symbols {
            type int32;
            config false;
            units "s";
            default -1;
        }
        leaf time2048SymbolsL {
            type int32;
            config false;
            units "s";
            default -1;
        }
        leaf time4096Symbols {
            type int32;
            config false;
            units "s";
            default -1;
        }
        leaf time4096SymbolsL {
            type int32;
            config false;
            units "s";
            default -1;
        }
        leaf time8192Symbols {
            type int32;
            config false;
            units "s";
            default -1;
        }
        leaf time8192SymbolsL {
            type int32;
            config false;
            units "s";
            default -1;
        }
        leaf snirMin {
            type int8;
            config false;
            description "Minimum signal to (noise+interference) ratio.";
            units "dB";
            default -99;
        }
        leaf snirMax {
            type int8;
            config false;
            description "Maximum signal to (noise+interference) ratio.";
            units "dB";
            default -99;
        }
        leaf snirAvg {
            type int8;
            config false;
            description "Averaged signal to (noise+interference) ratio.";
            units "dB";
            default -99;
        }
        leaf xpdMin {
            type int8;
            config false;
            description "Minimum cross polarization discrimination.";
            units "dB";
            default -99;
        }
        leaf xpdMax {
            type int8;
            config false;
            description "Maximum cross polarization discrimination.";
            units "dB";
            default -99;
        }
        leaf xpdAvg {
            type int8;
            config false;
            description "Averaged cross polarization discrimination.";
            units "dB";
            default -99;
        }
        leaf rfTempMin {
            type int8;
            config false;
            description "Lowest temperature (in degree Celsius) of the radio module inside the outdoor unit.";
            units "C";
            default -99;
        }
        leaf rfTempMax {
            type int8;
            config false;
            description "Highest temperature (in degree Celsius) of the radio module inside the outdoor unit.";
            units "C";
            default -99;
        }
        leaf rfTempAvg {
            type int8;
            config false;
            description "Averaged temperature (in degree Celsius) of the radio module inside the outdoor unit.";
            units "C";
            default -99;
        }
        leaf defectBlocksSum {
            type int16;
            config false;
            description "Total number of blocks that were defect after receiving and could not be corrected by the FEC.";
            units "blocks";
            default -1;
        }
        leaf timePeriod {
            type int32;
            config false;
            description "Total length of the measurement period.";
            units "s";
            default -1;
        }
    }
    grouping airInterfaceCurrentPerformanceType {
        description "Turns performance information into current performance information by inheriting from OTN_CurrentData.";
        uses G_874_1_model-Object_Classes:OTN_CurrentData;
        container performanceData {
            uses airInterfacePerformanceType;
        }
    }
    grouping airInterfaceHistoricalPerformanceType {
        description "Turns performance information into historical performance information by inheriting from OTN_HistoryData.";
        uses G_874_1_model-Object_Classes:OTN_HistoryData;
        container performanceData {
            uses airInterfacePerformanceType;
        }
    }
    typedef protectionType {
        type enumeration {
            enum hsb;
        }
    }
    typedef roleType {
        type enumeration {
            enum working;
            enum protection;
            enum protected;
        }
    }
    grouping diversityType {
        leaf diversityName {
            type string;
            config false;
            description "Names to be chosen from the following list: 'spaceDiversity', 'frequencyDiversity'";
        }
        leaf numberOfAirInterfacesMax {
            type int8;
            config false;
            description "Maximum number of air interfaces that could be part of this kind of diversity.";
            units "air interfaces";
            default 1;
        }
    }
    typedef airInterfaceDiversityStatusType {
        type enumeration {
            enum groupDown;
            enum notAllAiActive;
            enum allAiActive;
        }
    }
    grouping airInterfaceDiversityProblemSeverityType {
        leaf problemKindName {
            type string;
            description "Name of the alarm according to AirInterfaceDiversity::AirInterfaceDiversityCapability::supportedAlarms";
        }
        leaf problemKindSeverity {
            type severityType;
            description "Severity of this type of alarm.";
            default "warning";
        }
    }
    grouping airInterfaceDiversityCurrentProblemType {
        uses MicrowaveModel-ObjectClasses-SuperClasses:MwCurrentProblem;
        leaf problemName {
            type string;
            config false;
            description "Name of the alarm according to AirInterfaceDiversity::AirInterfaceDiversityCapability::supportedAlarms";
            default "Air interface diversity problems not yet defined.";
        }
        leaf problemSeverity {
            type severityType;
            description "Severity of the alarm.";
            default "warning";
        }
    }
    grouping airInterfaceDiversityPerformanceType {
        description "Consolidated performance information of the air interface diversity group.";
        leaf snirMin {
            type int8;
            config false;
            description "Minimum signal to (noise+interference) ratio of the combined signals.";
            units "dB";
            default -99;
        }
        leaf snirMax {
            type int8;
            config false;
            description "Maximum signal to (noise+interference) ratio of the combined signals.";
            units "dB";
            default -99;
        }
        leaf snirAvg {
            type int8;
            config false;
            description "Average signal to (noise+interference) ratio of the combined signals.";
            units "dB";
            default -99;
        }
    }
    grouping airInterfaceDiversityCurrentPerformanceType {
        description "Turns performance information into current performance information by inheriting from OTN_CurrentData.";
        uses G_874_1_model-Object_Classes:OTN_CurrentData;
        container performanceData {
            uses airInterfaceDiversityPerformanceType;
        }
    }
    grouping airInterfaceDiversityHistoricalPerformanceType {
        description "Turns performance information into historical performance information by inheriting from OTN_HistoryData.";
        uses G_874_1_model-Object_Classes:OTN_HistoryData;
        container performanceData {
            uses airInterfaceDiversityPerformanceType;
        }
    }
    grouping tdmStructureType {
        leaf tdmStructureName {
            type string;
            config false;
            description "Names to be chosen from the following list: 'e1','t1','j1','e3','ds3','stm1','cpri1','cpri2','cpri3','cpri4','cpri5','cpri6' or 'cpri7'";
        }
        leaf tdmSegmentSize {
            type int32;
            config false;
            description "Size of the TDM segment in kbit/s. Values to be chosen from the following list: '2048','1544','34000','44736 ','155520','614400','1228800','2457600','3072000','4915200','6144000' or '9830400;";
            units "kbit/s";
            default -1;
        }
        leaf maxNumberOfSegmentsReservable {
            type int8;
            config false;
            description "Device specific maximum number of segments (not depending on current air interface configuration) that can be reserved for this type of segment on a single air interface.";
            units "segments";
            default -1;
        }
    }
    grouping structureProblemSeverityType {
        leaf problemKindName {
            type string;
            description "Name of the alarm according to Structure::StructureCapability::supportedAlarms";
        }
        leaf problemKindSeverity {
            type severityType;
            description "Severity of this type of alarm.";
            default "warning";
        }
    }
    grouping structureCurrentProblemType {
        uses MicrowaveModel-ObjectClasses-SuperClasses:MwCurrentProblem;
        leaf problemName {
            type string;
            config false;
            description "Name of the alarm according to Structure::StructureCapability::supportedAlarms";
            default "Structure problems not yet defined.";
        }
        leaf problemSeverity {
            type severityType;
            description "Severity of the alarm.";
            default "warning";
        }
    }
    typedef structurePerformanceType {
        description "Consolidated performance information of the Structure.";
        type int32;
    }
    grouping structureCurrentPerformanceType {
        description "Turns performance information into current performance information by inheriting from OTN_CurrentData.";
        uses G_874_1_model-Object_Classes:OTN_CurrentData;
        leaf performanceData {
            type structurePerformanceType;
            config false;
        }
    }
    grouping structureHistoricalPerformanceType {
        description "Turns performance information into historical performance information by inheriting from OTN_HistoryData.";
        uses G_874_1_model-Object_Classes:OTN_HistoryData;
        leaf performanceData {
            type structurePerformanceType;
            config false;
        }
    }
    grouping tdmContainerType {
        leaf tdmContainerName {
            type string;
            config false;
            description "Names to be chosen from the following list: 'e1','t1','j1','e3','t3','stm1','cpri1','cpri2','cpri3','cpri4','cpri5','cpri6' or 'cpri7'";
        }
        leaf tdmContainerSize {
            type int32;
            config false;
            description "Capacity required for transporting this type of container (in kbit/s). Values to be chosen from the following list: '2048','1544','34000','44736 ','155520','614400','1228800','2457600','3072000','4915200','6144000' or '9830400;";
            units "kbit/s";
            default -1;
        }
    }
    grouping segmentIDType {
        description "Identifies the segments, which are used to transport the container.
            Combinations of structureId and segmentId must be unique inside the device to assure that every resource is used just once.";
        leaf structureIdRef {
            type CoreModel-CoreFoundationModule-SuperClassesAndCommonPackages:UniversalId;
        }
        leaf segmentIdRef {
            type int16;
        }
    }
    grouping segmentStatusType {
        leaf segmentStatusTypeId {
            type int16;
            config false;
        }
        leaf segmentIsReservedForTdm {
            type boolean;
            config false;
            description "The number of segments, which is configured by Structure::StructureConfiguration::tdmReservedNumberOfSegements, has to be reserved for TDM. Starting from the lowest index value, these segments have to be marked with a 'true' in segmentIsReservedForTdm.
                ";
            default false;
        }
        leaf operationalStatus {
            type CoreModel-CoreFoundationModule-StateModel:OperationalState;
            config false;
            description "Current operational status of each segment.";
            default "DISABLED";
        }
    }
    grouping containerProblemSeverityType {
        leaf problemKindName {
            type string;
            description "Name of the alarm according to Container::ContainerCapability::supportedAlarms";
        }
        leaf problemKindSeverity {
            type severityType;
            description "Severity of this type of alarm.";
            default "warning";
        }
    }
    grouping containerCurrentProblemType {
        uses MicrowaveModel-ObjectClasses-SuperClasses:MwCurrentProblem;
        leaf problemName {
            type string;
            config false;
            description "Name of the alarm according to Container::ContainerCapability::supportedAlarms";
            default "Container problems not yet defined.";
        }
        leaf problemSeverity {
            type severityType;
            description "Severity of the alarm.";
            default "warning";
        }
    }
    grouping containerPerformanceType {
        description "Consolidated performance information of the Container.";
        leaf txEthernetBytesMaxS {
            type int32;
            config false;
            description "Counts the number of Bytes of Ethernet traffic (before header compression) transmitted within a second and keeps the highest value within the measurement period. Field to be left blank for all types of TDM containers.
                Required data volume = 31bit";
            units "Bytes/s";
            default -1;
        }
        leaf txEthernetBytesMaxM {
            type int64;
            config false;
            description "Counts the number of Bytes of Ethernet traffic (before header compression) transmitted within a minute and keeps the highest value with in the measurement period. Field to be left blank for all types of TDM containers.
                Required data volume = 37bit";
            units "Bytes/min";
            default -1;
        }
        leaf txEthernetBytesSum {
            type int64;
            config false;
            description "Total number of Bytes of Ethernet traffic (before header compression) transmitted (in direction out of the device) during the measurement period. Field to be left blank for all types of TDM containers.
                Required data volume = 47bit";
            units "Bytes";
            default -1;
        }
        leaf timePeriod {
            type int32;
            config false;
            description "Total length of the measurement period in seconds.
                Required data volume = 17bit";
            units "s";
            default -1;
        }
    }
    grouping containerCurrentPerformanceType {
        description "Turns performance information into current performance information by inheriting from OTN_CurrentData.";
        uses G_874_1_model-Object_Classes:OTN_CurrentData;
        container performanceData {
            uses containerPerformanceType;
        }
    }
    grouping containerHistoricalPerformanceType {
        description "Turns performance information into historical performance information by inheriting from OTN_HistoryData.";
        uses G_874_1_model-Object_Classes:OTN_HistoryData;
        container performanceData {
            uses containerPerformanceType;
        }
    }
}
