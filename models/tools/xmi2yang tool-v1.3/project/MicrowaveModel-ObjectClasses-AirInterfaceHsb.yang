module MicrowaveModel-ObjectClasses-AirInterfaceHsb {
    namespace "uri:onf:MicrowaveModel-ObjectClasses-AirInterfaceHsb";
    prefix MicrowaveModel-ObjectClasses-AirInterfaceHsb;

    import MicrowaveModel-TypeDefinitions {
        prefix MicrowaveModel-TypeDefinitions;
    }
    import CoreModel-CoreNetworkModule-ObjectClasses {
        prefix CoreModel-CoreNetworkModule-ObjectClasses;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-09-13 {
        description 
            "Initial revision."; 
        reference 
            "ONF TR 532: A YANG Data Model for Microwave Transport Networks."; 
    }

    list MW_AirInterfaceHsbEndPoint_Pac {
        description "The EndPoint (EP) object class models the access to the FC function. Each EndPoint instance has a role (e.g., working, protection, protected, hub, spoke, leaf, root, etc.) with respect to the FC function. The association of the FC to LTPs is made via EndPoints (essentially the ports of the FC) where each EndPoint (EP) of the FC has a role in the context of the FC. The traffic forwarding between the associated End PointsEPs of the FC depends upon the type of FC and may be associated with FCSwitch object instances. In cases where there is protection conveys the protecting role of the access to the FC.  The EP replaces the Protection Unit of a traditional protection model. It represents a protected (resilient/reliable) point or a protecting (unreliable working or protection) point.";
        key 'endpoint';
        config true;
        leaf role {
            type MicrowaveModel-TypeDefinitions:roleType;
        }
        leaf endpoint {
            type leafref {
                path '/CoreModel-CoreNetworkModule-ObjectClasses:ForwardingConstruct/CoreModel-CoreNetworkModule-ObjectClasses:_fcPortList/CoreModel-CoreNetworkModule-ObjectClasses:uuid';
            }
        }
    }
    list MW_AirInterfaceHsbFcSwitch_Pac {
        description "Represents and defines a protection switch structure encapsulated in the forwarding construct. Essentially performs the function of Protection Group. Associates to 2 or more Endpoints each playing the role of a Protection Unit. One or more protection EndPoints (standby/backup) provide protection for one or more working (i.e. regular/main/preferred) Endpoints where either protection or working can feed one or more protected Endpoint. May be used in revertive or non-revertive (symmetric) mode. When in revertive mode may define waitToRestore time. May be used in one of several modes including source switch, destination switched, source and destination switched etc (covering cases such as  1+1 ane 1:1).  May be lockout (prevented from switching), force switched or manual switched. Will indicate switch state and change of state.";
        key 'fcswitch';
        config true;
        leaf protType {
            type MicrowaveModel-TypeDefinitions:protectionType;
            description "Indicates the protection scheme that is used for the ProtectionGroup.";
        }
        leaf airInterfaceHsbConfigurationIsFaultySeverity {
            type MicrowaveModel-TypeDefinitions:severityType;
            description "The level of severity of an airInterfaceHsbConfigurationIsFaulty alarm shall be chosen from an enumeration.";
        }
        leaf airInterfaceHsbIsPartlyDownSeverity {
            type MicrowaveModel-TypeDefinitions:severityType;
            description "The level of severity for one link out of the HSB configuration being down shall be chosen from an enumeration.";
        }
        leaf airInterfaceHsbIsDownSeverity {
            type MicrowaveModel-TypeDefinitions:severityType;
            description "The level of severity of the total HSB configuration being down shall be chosen from an enumeration.";
        }
        leaf fcswitch {
            type leafref {
                path '/CoreModel-CoreNetworkModule-ObjectClasses:ForwardingConstruct/CoreModel-CoreNetworkModule-ObjectClasses:_fcSwitchList/CoreModel-CoreNetworkModule-ObjectClasses:uuid';
            }
        }
    }
}
