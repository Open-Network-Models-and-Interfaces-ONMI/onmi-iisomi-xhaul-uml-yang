module core-model {
    yang-version 1.1;    namespace "undefined-core-model";
    prefix core-model;
    organization 
         "ONF (Open Networking Foundation) IMP Working Group";
    contact 
        "WG Web: <https://www.opennetworking.org/technical-communities/areas/services/>
        WG List: <mailto: <wg list name>@opennetworking.org>
        WG Chair: your-WG-chair
                <mailto:your-WG-chair@example.com>
        Editor: your-name
                <mailto:your-email@example.com>";
description
        "none";
    revision 1970-01-01 {
        description "Revision definition missing in papyrus uml.";
        reference "ONF-TR-512, RFC 6020 and RFC 6087";
    }
    /****************************************
    * package core-network-model
    **************************************/ 
/****************************************
* typedef statements
**************************************/ 
            typedef port-role {
                type string;
                description    
                "The role of a port in the context of the function of the forwarding entity that it bounds.";
            }
            typedef port-direction {
                type identityref {
                    base PORT_DIRECTION;
                }
                description    
                "The orientation of flow at the Port of a Forwarding entity.";
            }
            typedef forwarding-direction {
                type identityref {
                    base FORWARDING_DIRECTION;
                }
                description    
                "The directionality of a Forwarding entity.";
            }
            typedef termination-direction {
                type identityref {
                    base TERMINATION_DIRECTION;
                }
                description    
                "The directionality of a termination entity.";
            }
            typedef extended-termination-direction {
                type identityref {
                    base EXTENDED_TERMINATION_DIRECTION;
                }
                description    
                "Extended to include contra-direction considerations. Only applies to LP and elements of LP not to LTP.";
            }
            typedef termination-state {
                type identityref {
                    base TERMINATION_STATE;
                }
                description    
                "Provides support for the range of behaviors and specific states that an LP can take with respect to termination of the signal.
                    Indicates to what degree the LayerTermination is terminated.";
            }
            typedef layer-protocol-name {
                type identityref {
                    base LAYER_PROTOCOL_NAME;
                }
                description    
                "A controlled list of LayerProtocol names.";
            }

/*********************************************
* grouping statements for complex data types
*******************************************/ 
            identity PORT_DIRECTION {
                description    
                "none";
            }
            identity PORT_DIRECTION_BIDIRECTIONAL {
                base PORT_DIRECTION;
                description    
                "The Port has both an INPUT flow and an OUTPUT flow defined.";
            }
            identity PORT_DIRECTION_INPUT {
                base PORT_DIRECTION;
                description    
                "The Port only has definition for a flow into the Forwarding entity (i.e. an ingress flow).";
            }
            identity PORT_DIRECTION_OUTPUT {
                base PORT_DIRECTION;
                description    
                "The Port only has definition for a flow out of the Forwarding entity (i.e. an egress flow).";
            }
            identity PORT_DIRECTION_UNIDENTIFIED_OR_UNKNOWN {
                base PORT_DIRECTION;
                description    
                "Not a normal state. The system is unable to determine the correct value.";
            }
            identity PORT_DIRECTION_OMNIDIRECTIONAL {
                base PORT_DIRECTION;
                description    
                "none";
            }
            identity FORWARDING_DIRECTION {
                description    
                "none";
            }
            identity FORWARDING_DIRECTION_BIDIRECTIONAL {
                base FORWARDING_DIRECTION;
                description    
                "The Forwarding entity supports both BIDIRECTIONAL flows at all Ports (i.e. all Ports have both an INPUT flow and an OUTPUT flow defined).";
            }
            identity FORWARDING_DIRECTION_UNIDIRECTIONAL {
                base FORWARDING_DIRECTION;
                description    
                "The Forwarding entity has Ports that are either INPUT or OUTPUT. It has no BIDIRECTIONAL Ports.";
            }
            identity FORWARDING_DIRECTION_UNDEFINED_OR_UNKNOWN {
                base FORWARDING_DIRECTION;
                description    
                "Not a normal state. The system is unable to determine the correct value.";
            }
            identity FORWARDING_DIRECTION_OMNIDIRECTIONAL {
                base FORWARDING_DIRECTION;
                description    
                "none";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base TERMINATION_DIRECTION;
                description    
                "Not a normal state. The system is unable to determine the correct value.";
            }
            identity EXTENDED_TERMINATION_DIRECTION {
                description    
                "none";
            }
            identity EXTENDED_TERMINATION_DIRECTION_CONTRA_DIRECTION_SINK {
                base EXTENDED_TERMINATION_DIRECTION;
                description    
                "The essential flow of the Termination entity is SINK (i.e. up the layer stack) but the INPUT flow of the Termination entity was provided by a SOURCE OUTPUT or taken from a SOURCE INPUT (duplicating the input signal) hence reversing the flow orientation from down the layer stack to up the layer stack.";
            }
            identity EXTENDED_TERMINATION_DIRECTION_CONTRA_DIRECTION_SOURCE {
                base EXTENDED_TERMINATION_DIRECTION;
                description    
                "The essential flow of the Termination entity is SOURCE (i.e. down the layer stack) but the OUTPUT flow of the Termination entity was fed to (and replaces) a SINK OUTPUT or was fed to a SINK INPUT (replacing the normal flow) hence reversing the flow orientation from down the layer stack to up the layer stack.";
            }
            identity TERMINATION_STATE {
                description    
                "none";
            }
            identity TERMINATION_STATE_LP_CAN_NEVER_TERMINATE {
                base TERMINATION_STATE;
                description    
                "A non-flexible case that can never be terminated.";
            }
            identity TERMINATION_STATE_LP_NOT_TERMINATED {
                base TERMINATION_STATE;
                description    
                "A flexible termination that can terminate but is currently not terminated.";
            }
            identity TERMINATION_STATE_TERMINATED_SERVER_TO_CLIENT_FLOW {
                base TERMINATION_STATE;
                description    
                "A flexible termination that is currently terminated for server to client flow only.";
            }
            identity TERMINATION_STATE_TERMINATED_CLIENT_TO_SERVER_FLOW {
                base TERMINATION_STATE;
                description    
                "A flexible termination that is currently terminated for client to server flow only.";
            }
            identity TERMINATION_STATE_TERMINATED_BIDIRECTIONAL {
                base TERMINATION_STATE;
                description    
                "A flexible termination that is currently terminated in both directions of flow.";
            }
            identity TERMINATION_STATE_LP_PERMENANTLY_TERMINATED {
                base TERMINATION_STATE;
                description    
                "A non-flexible termination that is always terminated (in both directions of flow for a bidirectional case and in the one direction of flow for both unidirectional cases).";
            }
            identity TERMINATION_STATE_TERMINATION_STATE_UNKNOWN {
                base TERMINATION_STATE;
                description    
                "There TerminationState cannot be determined.";
            }
            identity PROTECTION_REASON {
                description    
                "none";
            }
            identity PROTECTION_REASON_WAIT_TO_REVERT {
                base PROTECTION_REASON;
                description    
                "The resource is selected as control is waiting to restore to a preferred resource.";
            }
            identity PROTECTION_REASON_SIGNAL_DEGRADE {
                base PROTECTION_REASON;
                description    
                "The resource is selected as the best preferred resource is in signal degrade.";
            }
            identity PROTECTION_REASON_SIGNAL_FAIL {
                base PROTECTION_REASON;
                description    
                "The resource is selected as the best preferred resource is in signal fail.";
            }
            identity ROUTE_SELECTION_CONTROL {
                description    
                "none";
            }
            identity ROUTE_SELECTION_CONTROL_LOCK_OUT {
                base ROUTE_SELECTION_CONTROL;
                description    
                "The resource is configured to temporarily not be available for use in the protection scheme(s) it is part of.
                    This overrides all other protection control states including forced.
                    If the item is locked out, then it cannot be used under any circumstances.
                    Note: Only relevant when part of a protection scheme.
                    Note: if a protection process that has a relationship to the item (i.e. is one of the options the protection process may choose) is deactivated by being isFrozen = true) then the lockout request will be rejected. ";
            }
            identity ROUTE_SELECTION_REASON {
                description    
                "none";
            }
            identity SWITCH_CONTROL {
                description    
                "none";
            }
            identity SWITCH_CONTROL_NORMAL {
                base SWITCH_CONTROL;
                description    
                "No administrative control applied to the switch.";
            }
            identity SWITCH_CONTROL_MANUAL {
                base SWITCH_CONTROL;
                description    
                "Resource temporarily chosen by control configuration where the resource is not the preferred resource.
                    Preferred resource has highest priority.
                    Temporarily overrides reversion.
                    If this resource fails, it will switch to best available resource. 
                    If resource selected is shared and another FC requires the resource, then the selection control will change to Normal and switch to best available based upon normal rules.
                    Cannot manually switch a Forced switch, cannot remove a forced switch, cannot switch to a locked out item and will be rejected if the protection process is deactivated by being Freeze = true).
                    A manual switch/route that is selecting an FcPort, LTP, FC, Link or Route that is subsequently set to LOCK_OUT will have the manual removed (changed to NORMAL) and will switch away from the FcPort with LOCK_OUT to best available based upon normal rules.
                    A manual switch that is selecting an FcPort that is subsequently selected by a Forced switch will be restored to normal operation and the manual will be removed.
                    A manual switch/route that is selecting an FcPort, LTP, FC, Link or Route that is subsequently manual selected by another switch/route will have the manual removed and will switch away from the FcPort.
                    Can be returned to NORMAL by configuration action.";
            }
            identity SWITCH_CONTROL_FORCED {
                base SWITCH_CONTROL;
                description    
                "Resource temporarily chosen by control configuration where the resource is not the preferred resource.
                    Preferred resource has highest priority.
                    Temporarily overrides reversion.
                    If this resource fails it will NOT switch. 
                    If resource selected is shared and another FC requires the resource through a FORCE on that FC and the FC is of a higher FcPriority then the selection control on this FC will change to NORMAL and switch to best available based upon normal rules.
                    If the resource selected is then set to LOCK_OUT then the selection control will change to NORMAL and switch to best available based upon normal rules.
                    Can be returned to NORMAL by configuration action.";
            }
            identity SWITCH_STATE_REASON {
                description    
                "none";
            }
            identity REVERSION_MODE {
                description    
                "none";
            }
            identity REVERSION_MODE_REVERTIVE {
                base REVERSION_MODE;
                description    
                "An FC switched to a lower priority (non-preferred) resource will revert to a higher priority (preferred) resource when that recovers (potentially after some hold-off time).";
            }
            identity REVERSION_MODE_NON-REVERTIVE {
                base REVERSION_MODE;
                description    
                "An FC switched to a lower priority (non-preferred) resource will not revert to a higher priority (preferred) resource when that recovers.";
            }
            identity RESILIENCE_CONTROL {
                description    
                "none";
            }
            identity RESILIENCE_CONTROL_QUIESCENT {
                base RESILIENCE_CONTROL;
                description    
                "none";
            }
            identity RESILIENCE_CONTROL_RESTORING {
                base RESILIENCE_CONTROL;
                description    
                "none";
            }
            identity RESILIENCE_CONTROL_RECOVERY_FAILED {
                base RESILIENCE_CONTROL;
                description    
                "none";
            }
            identity RESILIENCE_CONTROL_UNKNOWN {
                base RESILIENCE_CONTROL;
                description    
                "none";
            }
            identity RUN_MODE {
                description    
                "none";
            }
            identity RUN_MODE_FREE_RUN {
                base RUN_MODE;
                description    
                "The clock is not synchronized to another clock.";
            }
            identity RUN_MODE_LOCKED {
                base RUN_MODE;
                description    
                "The clock is synchronized to another clock.";
            }
            identity RUN_MODE_HOLD_OVER {
                base RUN_MODE;
                description    
                "The clock was previously synchronized to another clock but that timing input has been lost.
                    The clock is set to the last known synchronization.";
            }
            identity LAYER_PROTOCOL_NAME {
                description    
                "none";
            }
            identity LAYER_PROTOCOL_NAME_PHOTONIC_MEDIA {
                base LAYER_PROTOCOL_NAME;
                description    
                "The characteristic information is that of a channel able to carry photons and of the photon source/sink.";
            }
            identity LAYER_PROTOCOL_NAME_OTU_AND_ODU {
                base LAYER_PROTOCOL_NAME;
                description    
                "The characteristic information is that of a channel able to carry ODU/OTU protocol (OTN) and of the ODU/OTU source/sink.";
            }
            identity LAYER_PROTOCOL_NAME_ETHERNET {
                base LAYER_PROTOCOL_NAME;
                description    
                "The characteristic information is that of a channel able to carry Ethernet protocol and of the Ethernet protocol source/sink.";
            }
            identity OPERATIONAL_STATE {
                description    
                "none";
            }
            identity OPERATIONAL_STATE_DISABLED {
                base OPERATIONAL_STATE;
                description    
                "The resource is unable to meet the SLA of the user of the resource. 
                    If no (explicit) SLA is defined the resource is disabled if it is totally inoperable and unable to provide service to the user.";
            }
            identity OPERATIONAL_STATE_ENABLED {
                base OPERATIONAL_STATE;
                description    
                "The resource is partially or fully operable and available for use.";
            }
            identity ADMINISTRATIVE_STATE {
                description    
                "none";
            }
            identity ADMINISTRATIVE_STATE_LOCKED {
                base ADMINISTRATIVE_STATE;
                description    
                "Users are administratively prohibited from making use of the resource.";
            }
            identity ADMINISTRATIVE_STATE_UNLOCKED {
                base ADMINISTRATIVE_STATE;
                description    
                "Users are allowed to use the resource.";
            }
            identity ADMINISTRATIVE_STATE_SHUTTING_DOWN {
                base ADMINISTRATIVE_STATE;
                description    
                "The entity is administratively restricted to existing instances of use only. There may be specific actions to remove existing uses. No new instances of use can be enabled.
                    The resource automatically transitions to “locked” when the last user quits. 
                    The administrative state is not visible in the client context. 
                    The lifecycle state “pending removal” should be used to indicate to the client that the provider intends to remove the resource.";
            }
            identity ADMINISTRATIVE_CONTROL {
                description    
                "none";
            }
            identity ADMINISTRATIVE_CONTROL_UNLOCK {
                base ADMINISTRATIVE_CONTROL;
                description    
                "The intention is for the entity to become unlocked.
                    The entity may already be UNLOCKED.";
            }
            identity ADMINISTRATIVE_CONTROL_LOCK_PASSIVE {
                base ADMINISTRATIVE_CONTROL;
                description    
                "The intention is for the entity to become locked but no effort is expected to move to the Locked state (the state will be achieved once all users stop using the resource). 
                    The entity may be LOCKED.";
            }
            identity ADMINISTRATIVE_CONTROL_LOCK_ACTIVE {
                base ADMINISTRATIVE_CONTROL;
                description    
                "The intention is for the entity to become locked and it is expected that effort will be made to move to the Locked state (users will be actively removed). 
                    The entity may already be LOCKED.";
            }
            identity ADMINISTRATIVE_CONTROL_LOCK_IMMEDIATE {
                base ADMINISTRATIVE_CONTROL;
                description    
                "The intention is for the entity to become locked and it is expected to move to the Locked state immediately (users will be force removed). 
                    The entity may already be LOCKED.";
            }
            identity ADMINISTRATIVE_CONTROL_QUIESCENT {
                base ADMINISTRATIVE_CONTROL;
                description    
                "The administrative state is at a stable value (LOCKED/UNLOCKED) and no action is being taken.";
            }
            identity LIFECYCLE_STATE {
                description    
                "none";
            }
            identity LIFECYCLE_STATE_PLANNED {
                base LIFECYCLE_STATE;
                description    
                "The resource is planned but is not present in the network.
                    Should include a 'time' when the resources are expected to be installed.";
            }
            identity LIFECYCLE_STATE_POTENTIAL_AVAILABLE {
                base LIFECYCLE_STATE;
                description    
                "The supporting resources are present in the network but are shared with other clients; or require further configuration before they can be used; or both.
                    (1) When a potential resource is configured and allocated to a client it is moved to the INSTALLED state for that client.
                    (2) If the potential resource has been consumed (e.g. allocated to another client) it is moved to the POTENTIAL BUSY state for all other clients.";
            }
            identity LIFECYCLE_STATE_POTENTIAL_BUSY {
                base LIFECYCLE_STATE;
                description    
                "The supporting resources are present in the network but have been allocated to other clients.";
            }
            identity LIFECYCLE_STATE_INSTALLED {
                base LIFECYCLE_STATE;
                description    
                "The resource is present in the network and is capable of providing the service.";
            }
            identity LIFECYCLE_STATE_PENDING_REMOVAL {
                base LIFECYCLE_STATE;
                description    
                "The resource has been marked for removal. Should include a “time” when the resources are expected to be removed.";
            }
            identity BLOCK_DIRECTION {
                description    
                "none";
            }
            identity BLOCK_DIRECTION_NO_BLOCK {
                base BLOCK_DIRECTION;
                description    
                "The FC is not blocking signal related to the LTP.";
            }
            identity BLOCK_DIRECTION_INGRESS_BLOCK {
                base BLOCK_DIRECTION;
                description    
                "The FC is blocking signal that is flowing into the LTP from the FC.";
            }
            identity BLOCK_DIRECTION_EGRESS_BLOCK {
                base BLOCK_DIRECTION;
                description    
                "The FC is blocking signal flowing out of the LTP to the FC.";
            }
            identity BLOCK_DIRECTION_BIDIRECTIONAL_BLOCK {
                base BLOCK_DIRECTION;
                description    
                "The FC is blocking both directions of traffic, i.e. Ingress and Egress, to/from the LTP.";
            }
            identity CONNECTOR_AND_PIN_ORIENTATION {
                description    
                "none";
            }
            identity CONNECTOR_AND_PIN_ORIENTATION_MALE {
                base CONNECTOR_AND_PIN_ORIENTATION;
                description    
                "The connecting elements are dominantly protrusions.";
            }
            identity CONNECTOR_AND_PIN_ORIENTATION_FEMALE {
                base CONNECTOR_AND_PIN_ORIENTATION;
                description    
                "The connecting elements are dominantly indentations.";
            }
            identity CONNECTOR_AND_PIN_ORIENTATION_SYMMETRIC_NEUTRAL {
                base CONNECTOR_AND_PIN_ORIENTATION;
                description    
                "The pin (and housing) orientation combination is such that it is symmetric so a connector is compatible with itself.
                    The connecting element may be a surface rather than protrusions or indentations.";
            }
            identity EQUIPMENT_CATEGORY {
                description    
                "none";
            }
            identity EQUIPMENT_CATEGORY_SUBRACK {
                base EQUIPMENT_CATEGORY;
                description    
                "An assembly with holders designed to accommodate CIRCUIT_PACKs. 
                    The assembly is designed to be mounted in a RACK.";
            }
            identity EQUIPMENT_CATEGORY_CIRCUIT_PACK {
                base EQUIPMENT_CATEGORY;
                description    
                "An assembly with connectors compatible with those in a holder.
                    The assembly is designed to be mounted in a holder (SLOT) of a SUBRACK.
                    May also support holders (SLOTs) for SMALL_FORMFACTOR_PLUGGABLEs.";
            }
            identity EQUIPMENT_CATEGORY_SMALL_FORMFACTOR_PLUGGABLE {
                base EQUIPMENT_CATEGORY;
                description    
                "A small assembly (compared to a CIRCUIT_PACK) with connectors compatible with those in a holder.
                    The assembly is designed to be mounted in a holder (SLOT) of a CIRCUIT_PACK or STAND_ALONE_UNIT.";
            }
            identity EQUIPMENT_CATEGORY_STAND_ALONE_UNIT {
                base EQUIPMENT_CATEGORY;
                description    
                "An assembly with connectors for cabling and potentially with holders.
                    The assembly is designed to be mounted in a freeform environment (on a table or simple mechanical cabinet).
                    May support holders (SLOTs) for CIRCUIT_PACKs or for SMALL_FORMFACTOR_PLUGGABLEs.";
            }
            identity EQUIPMENT_CATEGORY_RACK {
                base EQUIPMENT_CATEGORY;
                description    
                "A mechanical assembly with cabling and predefined mounting points for particular SUBRACK types.
                    The assembly is designed to be mounted on the floor in a row with other RACKs.";
            }
            identity HOLDER_CATEGORY {
                description    
                "none";
            }
            identity HOLDER_CATEGORY_SLOT {
                base HOLDER_CATEGORY;
                description    
                "A guided holder with fixed connectors.
                    The guided holder is designed to take a particular form of CIRCUIT_PACK or SMALL_FORMFACTOR_PLUGGABLE";
            }
            identity FORWARDING_RULE {
                description    
                "none";
            }
            identity FORWARDING_RULE_CANNOT_FORWARD_ACROSS_FD_LINK {
                base FORWARDING_RULE;
                description    
                "LTPs referenced by the FD (or indirectly by the Link between FDs) cannot have FCs created between them.
                    This rule overrides all others.";
            }
            identity FORWARDING_RULE_MUST_FORWARD_ACROSS_FD_LINK {
                base FORWARDING_RULE;
                description    
                "LTPs referenced by the FD (or indirectly by the Link between FDs) MUST have FCs created between them.
                    This rule overrides all others except the CANNOT_FORWARD rule.";
            }
            identity FORWARDING_RULE_MAY_FORWARD_ACROSS_FD_LINK {
                base FORWARDING_RULE;
                description    
                "LTPs referenced by the FD (or indirectly by the Link between FDs) may have FCs created between them.
                    FCs may not be created between points that are not related by this rule either directly in an FD or indirectly via a Link linking two or more FDs.
                    For a Link points in an FD at one end of the Link can be connected to points in an FD at an other end of the Link.";
            }
            identity FORWARDING_RULE_NULL_FORWARDING_RULE {
                base FORWARDING_RULE;
                description    
                "none";
            }
            identity RULE_TYPE {
                description    
                "none";
            }
            identity RULE_TYPE_FORWARDING {
                base RULE_TYPE;
                description    
                "The rule relates to creation of FCs.";
            }
            identity RULE_TYPE_COST {
                base RULE_TYPE;
                description    
                "The rule relates to forwarding cost.";
            }
            identity RULE_TYPE_RISK {
                base RULE_TYPE;
                description    
                "The rule relates to forwarding risk.";
            }
            identity RULE_TYPE_CAPACITY {
                base RULE_TYPE;
                description    
                "none";
            }
            identity PORT_ROLE_RULE_OPTION {
                description    
                "none";
            }
            identity PORT_ROLE_RULE_OPTION_SAME_ROLE {
                base PORT_ROLE_RULE_OPTION;
                description    
                "The ports to which the rule applies must have role from the list in PortRole.";
            }
            identity PORT_ROLE_RULE_OPTION_DIFFERENT_ROLE {
                base PORT_ROLE_RULE_OPTION;
                description    
                "The ports to which the rule applies must not have a role from the list in PortRole.";
            }
            identity PORT_ROLE_RULE_OPTION_ANY_ROLE {
                base PORT_ROLE_RULE_OPTION;
                description    
                "The rule applies to any role of port.";
            }
            identity SIGNAL_PROPERTY_VALUE_RULE {
                description    
                "none";
            }
            identity SIGNAL_PROPERTY_VALUE_RULE_SAME_VALUE {
                base SIGNAL_PROPERTY_VALUE_RULE;
                description    
                "none";
            }
            identity SIGNAL_PROPERTY_VALUE_RULE_ANY_VALUE {
                base SIGNAL_PROPERTY_VALUE_RULE;
                description    
                "none";
            }
            identity PARTNER {
                description    
                "none";
            }
            identity PARTNER_FC {
                base PARTNER;
                description    
                "ForwardingConstruct.";
            }
            identity PARTNER_FD {
                base PARTNER;
                description    
                "ForwardingDomain.";
            }
            identity PARTNER_LINK {
                base PARTNER;
                description    
                "Link.";
            }
            identity PARTNER_CASC {
                base PARTNER;
                description    
                "ConfigurationAndSwitchController.";
            }
            identity PARTNER_CC {
                base PARTNER;
                description    
                "ControlConstruct.";
            }
            identity PARTNER_CD {
                base PARTNER;
                description    
                "ConstraintDomain.";
            }
            identity PARTNER_PC {
                base PARTNER;
                description    
                "ProcessingConstruct.";
            }
            identity PARTNER_PEER {
                base PARTNER;
                description    
                "LTP peer.";
            }
            identity PARTNER_CLIENT {
                base PARTNER;
                description    
                "LTP client.";
            }
            identity PARTNER_SERVER {
                base PARTNER;
                description    
                "LTP server.";
            }
            identity PARTNER_VIEW {
                base PARTNER;
                description    
                "LTP in other view.";
            }
            identity TASK_LIFECYCLE_STATE {
                description    
                "none";
            }
            identity TASK_LIFECYCLE_STATE_RUNNING {
                base TASK_LIFECYCLE_STATE;
                description    
                "The task is running.";
            }
            identity TASK_LIFECYCLE_STATE_PAUSED {
                base TASK_LIFECYCLE_STATE;
                description    
                "The task has been paused.";
            }
            identity TASK_LIFECYCLE_STATE_WAITING {
                base TASK_LIFECYCLE_STATE;
                description    
                "The task is waiting for input etc.";
            }
            identity TASK_LIFECYCLE_STATE_ABORTING {
                base TASK_LIFECYCLE_STATE;
                description    
                "The task is aborting.";
            }
            identity TASK_LIFECYCLE_STATE_COMPLETED {
                base TASK_LIFECYCLE_STATE;
                description    
                "The task has been completed successfully.";
            }
            identity TASK_LIFECYCLE_STATE_ABORTED {
                base TASK_LIFECYCLE_STATE;
                description    
                "The task has been aborted.";
            }
            identity TASK_LIFECYCLE_STATE_ATTEMPTING_ROLLBACK {
                base TASK_LIFECYCLE_STATE;
                description    
                "The task is attempting to return the controlled system to a previous state.";
            }
            identity TASK_LIFECYCLE_STATE_ROLLBACK_COMPLETE {
                base TASK_LIFECYCLE_STATE;
                description    
                "The task has completed a roll back action.";
            }
            identity TASK_LIFECYCLE_STATE_ABANDONING {
                base TASK_LIFECYCLE_STATE;
                description    
                "Task is abandoning.";
            }
            identity TASK_LIFECYCLE_STATE_ABANDONED {
                base TASK_LIFECYCLE_STATE;
                description    
                "The task has been abandoned and is no longer running.";
            }
            identity TASK_LIFECYCLE_STATE_FAILED {
                base TASK_LIFECYCLE_STATE;
                description    
                "The task has failed.";
            }
            identity TASK_LIFECYCLE_STATE_ARCHIVED {
                base TASK_LIFECYCLE_STATE;
                description    
                "The task has been archived (and is no longer running).";
            }
            identity PROGRESS_STATUS {
                description    
                "none";
            }
            identity PROGRESS_STATUS_COMPLETE {
                base PROGRESS_STATUS;
                description    
                "none";
            }
            identity PROGRESS_STATUS_IN_PROGRESS {
                base PROGRESS_STATUS;
                description    
                "none";
            }
            identity PROGRESS_STATUS_FAILED {
                base PROGRESS_STATUS;
                description    
                "none";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity.";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity.";
            }
            identity TERMINATION_DIRECTION_UNDEFINED_OR_UNKNOWN {
                base TERMINATION_DIRECTION;
                description    
                "Not a normal state. The system is unable to determine the correct value.";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base TERMINATION_DIRECTION;
                description    
                "Not a normal state. The system is unable to determine the correct value.";
            }
            identity ACTION_VERBS {
                description    
                "none";
            }
            identity ACTION_VERBS_CREATE_POST_ADD {
                base ACTION_VERBS;
                description    
                "none";
            }
            identity ACTION_VERBS_SET_UPDATE_PUT_MODIFY_WRITE_ADD {
                base ACTION_VERBS;
                description    
                "none";
            }
            identity ACTION_VERBS_GET_READ {
                base ACTION_VERBS;
                description    
                "none";
            }
            identity ACTION_VERBS_DELETE_REMOVE {
                base ACTION_VERBS;
                description    
                "none";
            }
            identity DIRECTION {
                description    
                "none";
            }
            identity DIRECTION_IN {
                base DIRECTION;
                description    
                "none";
            }
            identity DIRECTION_OUT {
                base DIRECTION;
                description    
                "none";
            }
            identity DIRECTION_BIDIRECTIONAL {
                base DIRECTION;
                description    
                "none";
            }
            identity ACTION_VERBS {
                description    
                "none";
            }
            identity ACTION_VERBS_CREATE_POST_ADD {
                base ACTION_VERBS;
                description    
                "Cause the addition of some structure.";
            }
            identity ACTION_VERBS_SET_UPDATE_PUT_MODIFY_WRITE_ADD {
                base ACTION_VERBS;
                description    
                "Cause the adjustment to some properties.";
            }
            identity ACTION_VERBS_GET_READ {
                base ACTION_VERBS;
                description    
                "Acquire information.";
            }
            identity ACTION_VERBS_DELETE_REMOVE {
                base ACTION_VERBS;
                description    
                "Eliminate some structure.";
            }
            identity ACTIVITY_DIRECTIVE {
                description    
                "none";
            }
            identity ACTIVITY_DIRECTIVE_STRUCTURE_IS_NOT {
                base ACTIVITY_DIRECTIVE;
                description    
                "The structure defined should not be present. No part should be present (within the stated degrees of precision.";
            }
            identity ACTIVITY_DIRECTIVE_NEW_STRUCTURE_AND_VALUES {
                base ACTIVITY_DIRECTIVE;
                description    
                "None of the structure stated is expected to be present, but is required.";
            }
            identity ACTIVITY_DIRECTIVE_INCREMENTAL_STRUCTURE_AND_VALUES {
                base ACTIVITY_DIRECTIVE;
                description    
                "The structure stated is an increment on what already exists.
                    Increment in this case may also be decrement.";
            }
            identity ACTIVITY_DIRECTIVE_ONLY_VALUES_IN_EXISTING_STRUCTURE {
                base ACTIVITY_DIRECTIVE;
                description    
                "Only values should be modified, no new structure should be created and no structure should be deleted.";
            }
            identity ACTIVITY_DIRECTIVE_DEFINED_BY_VERB {
                base ACTIVITY_DIRECTIVE;
                description    
                "A verb is provided to give guidance (such as Create).";
            }
            identity ACTION_EFFORT {
                description    
                "none";
            }
            identity ACTION_EFFORT_BEST_EFFORT {
                base ACTION_EFFORT;
                description    
                "none";
            }
            identity ACTION_EFFORT_EXACT_MATCH {
                base ACTION_EFFORT;
                description    
                "none";
            }
            identity PAUSE_RESUME_RULE {
                description    
                "none";
            }
            identity PAUSE_RESUME_RULE_NO_PAUSE_POSSIBLE {
                base PAUSE_RESUME_RULE;
                description    
                "none";
            }
            /****************************************
            * package topology
            **************************************/ 
                grouping cost-characteristics {
                    leaf cost-name {
                        type string;
                        description    
                    "The cost characteristic is related to some aspect of the ForwardingEntity (e.g. $ cost, routing weight). This aspect will be conveyed by the costName.";
                    }
                    leaf cost-value {
                        type string;
                        description    
                    "The specific cost.";
                    }
                    leaf cost-algorithm {
                        type to-be-defined;
                        description    
                    "The cost may vary based upon some properties of the ForwardingEntity. The rules for the variation are conveyed by the costAlgorithm.";
                    }
                    description    
                "The information for a particular cost characteristic.";
                }
                grouping risk-characteristic {
                    leaf risk-characteristic-name {
                        type string;
                        description    
                    "The name of the risk characteristic. The characteristic may be related to a specific degree of closeness. 
                            For example, a particular characteristic may apply to failures that are localized (e.g. to one side of a road) where as another characteristic may relate to failures that have a broader impact (e.g. both sides of a road that crosses a bridge).
                            Depending upon the importance of the traffic being routed different risk characteristics will be evaluated.";
                    }
                    leaf-list risk-identifier {
                        type string;
                        min-elements 1;
                        description     
                 "A list of the identifiers of each physical/geographic unit (with the specific risk characteristic) that is related to a segment of the ForwardingEntity.";
                    }
                    description    
                "The information for a particular risk characteristic where there is a list of risk identifiers related to that characteristic.";
                }
                grouping capacity {
                    leaf total-size {
                        type string;
                        description    
                    "Total capacity of the ForwardingEntity in Mbits/s.";
                    }
                    leaf number-of-client-instances {
                        type string;
                        description    
                    "Where there is some limit to the number of client (e.g. in a channelized case).";
                    }
                    leaf maximum-client-size {
                        type string;
                        description    
                    "Where a client is of variable capacity but due to some underlying realization the maximum size of the client is smaller than the totalSize.";
                    }
                    leaf numbering-range {
                        type string;
                        description    
                    "Method for identifying units of capacity via some numbering scheme.";
                    }
                    description    
                "Information on capacity of a particular ForwardingEntity.";
                }
                grouping validation-mechanism {
                    leaf validation-mechanism {
                        type string;
                        description    
                    "Name of mechanism used to validate adjacency.";
                    }
                    leaf layer-protocol-adjacency-validated {
                        type string;
                        description    
                    "State of validation.";
                    }
                    leaf validation-robustness {
                        type string;
                        description    
                    "Quality of validation (i.e. how likely is the stated validation to be invalid).";
                    }
                    description    
                "Identifies the validation mechanism and describes the characteristics of that mechanism.";
                }
                grouping queuing-latency {
                    leaf traffic-property {
                        type string;
                        description    
                    "The identifier of the specific traffic property to which the queuing latency applies.";
                    }
                    leaf latency-for-traffic-with-property {
                        type string;
                        description    
                    "The specific queuing latency for the traffic property.";
                    }
                    description    
                "Provides information on latency characteristic for a particular stated trafficProperty.";
                }

            /****************************************
            * package resilience
            **************************************/ 
                typedef protection-reason {
                    type identityref {
                        base PROTECTION_REASON;
                    }
                    description    
                "The cause of the current protection state.";
                }
                typedef route-selection-control {
                    type identityref {
                        base ROUTE_SELECTION_CONTROL;
                    }
                    description    
                "Possible degrees of administrative control applied to the Route selection.";
                }
                typedef route-selection-reason {
                    type identityref {
                        base ROUTE_SELECTION_REASON;
                    }
                    description    
                "The cause of the current route selection.";
                }
                typedef switch-control {
                    type identityref {
                        base SWITCH_CONTROL;
                    }
                    description    
                "none";
                }
                typedef switch-state-reason {
                    type identityref {
                        base SWITCH_STATE_REASON;
                    }
                    description    
                "Explains the reason for the current switch state.";
                }
                typedef reversion-mode {
                    type identityref {
                        base REVERSION_MODE;
                    }
                    description    
                "The reversion mode associated with protection.";
                }
                grouping global-pac {
                    uses global-class;
                    description    
                "Provides the properties of a GlobalClass via composition.";
                }
                grouping local-pac {
                    uses local-class;
                    description    
                "Provides the properties of a LocalClass via composition.";
                }
                typedef protection-type {
                    type string;
                    description    
                "Identifies the type of protection of an FcSwitch.";
                }
                typedef resilience-control {
                    type identityref {
                        base RESILIENCE_CONTROL;
                    }
                    description    
                "none";
                }

            /****************************************
            * package timing
            **************************************/ 
                typedef run-mode {
                    type identityref {
                        base RUN_MODE;
                    }
                    description    
                "none";
                }

            grouping layer-protocol-name-and-qualifier {
                leaf layer-protocol-qualifier {
                    type string;
                    description    
                    "Qualifies the use of the LayerProtocol where the same LayerProtocol may be used recursively such that each recursion has the same characteristic information in the main traffic path but where there is some distinction in some other aspect.
                        An example of use is in the case of the PHOTONIC_MEDIA LayerProtocol. All photonic media is of the same characteristic in the main traffic path, just a channel that enables the flow of photons, but may differ in overhead and with respect to level of nesting.
                        For the PHOTONIC_MEDIA, qualifiers may include OMS (Optical Multiplex Section), OTS (Optical Transmission Section) and NMCA (Network Media Channel Assembly).";
                }
                leaf layer-protocol-name {
                    type string;
                    description    
                    "The name of the LayerProtocol chosen from a controlled list.
                        LayerProtocol names include:
                        - PHOTONIC_MEDIA
                        - ODU
                        - ETHERNET";
                }
                description    
                "Provides a controlled list of layer protocol names and indicates the naming authority.
                    Note that it is expected that attributes will be added to this structure to convey the naming authority name, the name of the layer protocol using a human readable string and any particular standard reference.
                    Layer protocol names include:
                    -    Layer 1 (L1): OTU, ODU
                    -    Layer 2 (L2): Carrier Grade Ethernet (ETY, ETH), MPLS-TP (MT)
                    ";
            }

        /****************************************
        * grouping statements for object classes
        **************************************/ 
            /****************************************
            * package topology
            **************************************/ 
                grouping transfer-cost-pac {
                    list cost-characteristic {
                        min-elements 1;
                        uses cost-characteristics;
                        description    
                "The list of costs where each cost relates to some aspect of the ForwardingEntity.";
                    }
                    description    
                "The cost characteristics of a ForwardingEntity not necessarily correlated to the cost of the underlying physical realization. 
                        They may be quite specific to the individual ForwardingEntity (e.g. opportunity cost) and relates to layer capacity
                        There may be many perspectives from which cost may be considered for a particular ForwardingEntity and hence many specific costs and potentially cost algorithms. 
                        Using an entity will incur a cost. ";
                }
                grouping risk-parameter-pac {
                    list risk-characteristic {
                        min-elements 1;
                        uses risk-characteristic;
                        description    
                "A list of risk characteristics for consideration in an analysis of shared risk. Each element of the list represents a specific risk consideration.";
                    }
                    description    
                "The risk characteristics of a ForwardingEntity come directly from the underlying physical realization. 
                        The risk characteristics propagate from the physical realization to the client and from the server layer to the client layer; this propagation may be modified by protection.
                        A ForwardingEntity may suffer degradation or failure as a result of a problem in a part of the underlying realization.
                        The realization can be partitioned into segments which have some relevant common failure modes.
                        There is a risk of failure/degradation of each segment of the underlying realization.
                        Each segment is a part of a larger physical/geographical unit that behaves as one with respect to failure (i.e. a failure will have a high probability of impacting the whole unit (e.g. all cables in the same duct).
                        Disruptions to that larger physical/geographical unit will impact (cause failure/errors to) all ForwardingEntities that use any part of that larger physical/geographical entity.
                        Any ForwardingEntity that uses any part of that larger physical/geographical unit will suffer impact and hence each ForwardingEntity shares risk.
                        The identifier of each physical/geographical unit that is involved in the realization of each segment of a ForwardingEntity can be listed in the RiskParameter_Pac of that ForwardingEntity.
                        A segment has one or more risk characteristic.
                        Shared risk between two ForwardingEntities compromises the integrity of any solution that use one of those ForwardingEntity as a backup for the other.
                        Where two ForwardingEntities have a common risk characteristic they have an elevated probability of failing simultaneously compared to two ForwardingEntities that do not share risk characteristics.";
                }
                grouping layer-protocol-transition-pac {
                    leaf-list transitioned-layer-protocol {
                        type string;
                        min-elements 2;
                        description     
                 "Provides the ordered structure of layer protocol transitions encapsulated in the ForwardingEntity. 
                            The list starts with the client side as the first entry and includes all layer-protocol names (hence the smallest number is 2 as otherwise the Link is not transitional). 
                            The ordering relates also to the LinkPort role (which emphasizes the orientation). 
                            Where the transitional link is multi-ported and layer asymmetric the list includes the superset of layer-protocol names. 
                            Transitional links can only be applied where the transition for each port is such that all transitions between any ports are subsequences of the list. 
                            The specific subsequence is determined by the LayerProtocols of the LTP associated with the LinkPort and the role of the LinkPort.";
                    }
                    list ltp {
                        min-elements 1;
                        uses logical-termination-point;
                        description    
                "Lists the LTPs that define the layer protocol transition of the transitional link.";
                    }
                    description    
                "The transition characteristics are relevant for a Link that is formed by abstracting one or more LTPs (in a stack) to focus on the flow and deemphasize the protocol transformation. 
                        This abstraction is relevant when considering multi-layer routing. 
                        The layer protocols of the LTP and the order of their application to the signal is still relevant and needs to be accounted for (this is derived from the LTP spec details).
                        This Pac provides the relevant abstractions of the LTPs and provides the necessary association to the LTPs involved.
                        Links that include details in this Pac are often referred to as Transitional Links.";
                }
                grouping transfer-timing-pac {
                    leaf fixed-latency-characteristic {
                        type string;
                        description    
                    "A ForwardingEntity suffers delay caused by the realization of the servers (e.g. distance related; FEC encoding etc.) along with some client specific processing. This is the total average latency effect of the ForwardingEntity.";
                    }
                    leaf jitter-characteristic {
                        if-feature present-if-jittercharacteristic-information-is-relevant-to-usage-and-statement-can-be-made-that-applies-equally-to-all-flows-that-can-be-supported-by-the-forwardingentity
note-that-if-jittercharacteristic-is-relevant-but-consistent-statement-cannot-be-made-then-the-forwardingentity-should-be-described-in-terms-of-subordinate-parts-against-which-coherent-statements-can-be-made
note-that-this-only-applies-to-tdm;
                        type string;
                        description    
                    "High frequency deviation from true periodicity of a signal and therefore a small high rate of change of transfer latency.
                            Applies to TDM systems (and not packet).";
                    }
                    leaf wander-characteristic {
                        if-feature present-if-wandercharacteristic-information-is-relevant-to-usage-and-statement-can-be-made-that-applies-equally-to-all-flows-that-can-be-supported-by-the-forwardingentity
note-that-if-wandercharacteristic-is-relevant-but-consistent-statement-cannot-be-made-then-the-forwardingentity-should-be-described-in-terms-of-subordinate-parts-against-which-coherent-statements-can-be-made
note-that-this-only-applies-to-tdm;
                        type string;
                        description    
                    "Low frequency deviation from true periodicity of a signal and therefore a small low rate of change of transfer latency.
                            Applies to TDM systems (and not packet).";
                    }
                    list queuing-latency-characteristic {
                        if-feature present-if-queuinglatencycharacteristic-information-is-relevant-to-usage-and-statement-can-be-made-that-applies-equally-to-all-flows-that-can-be-supported-by-the-forwardingentity
there-may-be-more-than-one-instance-if-the-queuing-behavior-depends-upon-traffic-properties
note-that-if-queuinglatencycharacteristic-is-relevant-but-consistent-statement-cannot-be-made-then-the-forwardingentity-should-be-described-in-terms-of-subordinate-parts-against-which-coherent-statements-can-be-made
note-that-this-only-applies-to-packet-system;
                        uses queuing-latency;
                        description    
                "The effect on the latency of a queuing process. This only has significant effect for packet based systems and has a complex characteristic.";
                    }
                    description    
                "A ForwardingEntity will suffer effects from the underlying physical realization related to the timing of the information passed by the ForwardingEntity.";
                }
                grouping transfer-integrity-pac {
                    leaf error-characteristic {
                        if-feature present-if-errorcharacteristic-information-is-relevant-to-usage-and-statement-can-be-made-that-applies-equally-to-all-flows-that-can-be-supported-by-the-forwardingentity
note-that-if-errorcharacteristic-is-relevant-but-consistent-statement-cannot-be-made-then-the-forwardingentity-should-be-described-in-terms-of-subordinate-parts-against-which-coherent-statements-can-be-made
note-that-this-only-applies-to-tdm;
                        type string;
                        description    
                    "Describes the degree to which the signal propagated can be errored. 
                            Applies to TDM systems as the errored signal will be propagated and not packet as errored packets will be discarded.";
                    }
                    leaf loss-characteristic {
                        if-feature present-if-losscharacteristic-information-is-relevant-to-usage-and-statement-can-be-made-that-applies-equally-to-all-flows-that-can-be-supported-by-the-forwardingentity
note-that-if-losscharacteristic-is-relevant-but-consistent-statement-cannot-be-made-then-the-forwardingentity-should-be-described-in-terms-of-subordinate-parts-against-which-coherent-statements-can-be-made
note-that-this-only-applies-to-packet-systems;
                        type string;
                        description    
                    "Describes the acceptable characteristic of lost packets where loss may result from discard due to errors or overflow.
                            Applies to packet systems and not TDM (as for TDM errored signals are propagated unless grossly errored and overflow/underflow turns into timing slips).";
                    }
                    leaf repeat-delivery-characteristic {
                        if-feature present-if-repeatdeliverycharacteristic-information-is-relevant-to-usage-and-statement-can-be-made-that-applies-equally-to-all-flows-that-can-be-supported-by-the-forwardingentity
note-that-if-repeatdeliverycharacteristic-is-relevant-but-consistent-statement-cannot-be-made-then-the-forwardingentity-should-be-described-in-terms-of-subordinate-parts-against-which-coherent-statements-can-be-made
note-that-this-primarily-applies-to-packet-systems-where-a-packet-may-be-delivered-more-than-once-(in-fault-recovery-for-example)
note-that-it-can-also-apply-to-tdm-where-several-frames-may--be-received-twice-due-to-switching-in-a-system-with-a-large-differential-propagation-delay;
                        type string;
                        description    
                    "Primarily applies to packet systems where a packet may be delivered more than once (in fault recovery for example). 
                            It can also apply to TDM where several frames may be received twice due to switching in a system with a large differential propagation delay.";
                    }
                    leaf delivery-order-characteristic {
                        if-feature present-if-deliveryordercharacteristic-information-is-relevant-to-usage-and-statement-can-be-made-that-applies-equally-to-all-flows-that-can-be-supported-by-the-forwardingentity
note-that-if-deliveryordercharacteristic-is-relevant-but-consistent-statement-cannot-be-made-then-the-forwardingentity-should-be-described-in-terms-of-subordinate-parts-against-which-coherent-statements-can-be-made
note-that-this-only-applies-to-packet-systems
;
                        type string;
                        description    
                    "Describes the degree to which packets will be delivered out of sequence.
                            Does not apply to TDM as the TDM protocols maintain strict order.";
                    }
                    leaf unavailable-time-characteristic {
                        type string;
                        description    
                    "Describes the duration for which there may be no valid signal propagated.";
                    }
                    leaf server-integrity-process-characteristic {
                        if-feature present-if-serverintegrityprocesscharacteristic-information-is-relevant-to-usage-and-statement-can-be-made-that-applies-equally-to-all-flows-that-can-be-supported-by-the-forwardingentity
note-that-if-serverintegrityprocesscharacteristic-is-relevant-but-consistent-statement-cannot-be-made-then-the-forwardingentity-should-be-described-in-terms-of-subordinate-parts-against-which-coherent-statements-can-be-made
note-that-this-only-applies-where-the-server-has-some-error-recovery-mechanism-alters-the-characteristics-of-the-link-from-a-normal-distribution;
                        type string;
                        description    
                    "Describes the effect of any server integrity enhancement process on the characteristics of the ForwardingEntity.";
                    }
                    description    
                "Transfer integrity characteristic covers expected/specified/acceptable characteristic of degradation of the transferred signal.
                        It includes all aspects of possible degradation of signal content as well as any damage of any form to the total ForwardingEntity and to the carried signals.
                        Note that the statement is of total impact to the ForwardingEntity so any partial usage of the ForwardingEntity (e.g. a signal that does not use full capacity) will only suffer its portion of the impact.";
                }
                grouping transfer-capacity-pac {
                    container total-potential-capacity {
                        uses capacity;
                        description    
                "An optimistic view of the capacity of the ForwardingEntity assuming that any shared capacity is available to be taken.";
                    }
                    container available-capacity {
                        uses capacity;
                        description    
                "Capacity available to be assigned.";
                    }
                    list capacity-assigned-to-user-view {
                        uses capacity;
                        description    
                "Capacity already assigned.";
                    }
                    leaf capacity-interaction-algorithm {
                        type string;
                        description    
                    "A reference to an algorithm that describes how various chunks of allocated capacity interact (e.g. when shared).";
                    }
                    description    
                "The ForwardingEntity derives capacity from the underlying realization. 
                        A ForwardingEntity may be an abstraction and virtualization of a subset of the underlying capability offered in a view or may be directly reflecting the underlying realization.
                        A ForwardingEntity may be directly used in the view or may be assigned to another view for use.
                        The clients supported by a multi-layer ForwardingEntity may interact such that the resources used by one client may impact those available to another. This is derived from the LTP spec details.
                        Represents the capacity available to user (client) along with client interaction and usage. 
                        A ForwardingEntity may reflect one or more client protocols and one or more members for each profile.";
                }
                grouping forwarding-entity {
                    container risk-parameter-pac {
                        if-feature present-if-risk-information-is-relevant-to-usage-and-statement-can-be-made-that-applies-equally-to-all-flows-that-can-be-supported-by-the-forwardingentity
note-that-if-risk-is-relevant-but-consistent-statement-cannot-be-made-then-the-forwardingentity-should-be-described-in-terms-of-subordinate-parts-against-which-coherent-statements-can-be-made;
                        uses risk-parameter-pac;
                        description    
                "none";
                    }
                    container transfer-cost-pac {
                        if-feature present-if-cost-information-is-relevant-to-usage-and-statement-can-be-made-that-applies-equally-to-all-flows-that-can-be-supported-by-the-forwardingentity
note-that-if-cost-is-relevant-but-consistent-statement-cannot-be-made-then-the-forwardingentity-should-be-described-in-terms-of-subordinate-parts-against-which-coherent-statements-can-be-made;
                        uses transfer-cost-pac;
                        description    
                "none";
                    }
                    container transfer-timing-pac {
                        if-feature present-if-transfer-timing-information-is-relevant-to-usage-and-statement-can-be-made-that-applies-equally-to-all-flows-that-can-be-supported-by-the-forwardingentity
note-that-if-transfer-timing-is-relevant-but-consistent-statement-cannot-be-made-then-the-forwardingentity-should-be-described-in-terms-of-subordinate-parts-against-which-coherent-statements-can-be-made;
                        uses transfer-timing-pac;
                        description    
                "none";
                    }
                    container transfer-capacity-pac {
                        if-feature present-if-transfer-capacity-information-is-relevant-to-usage-and-statement-can-be-made-that-applies-equally-to-all-flows-that-can-be-supported-by-the-forwardingentity
note-that-if-transfer-capacity-is-relevant-but-consistent-statement-cannot-be-made-then-the-forwardingentity-should-be-described-in-terms-of-subordinate-parts-against-which-coherent-statements-can-be-made;
                        uses transfer-capacity-pac;
                        description    
                "none";
                    }
                    container transfer-integrity-pac {
                        if-feature present-if-transfer-integrity-information-is-relevant-to-usage-and-statement-can-be-made-that-applies-equally-to-all-flows-that-can-be-supported-by-the-forwardingentity
note-that-if-transfer-integrity-is-relevant-but-consistent-statement-cannot-be-made-then-the-forwardingentity-should-be-described-in-terms-of-subordinate-parts-against-which-coherent-statements-can-be-made;
                        uses transfer-integrity-pac;
                        description    
                "none";
                    }
                    container validation-pac {
                        if-feature present-if-validation-information-is-relevant-to-usage-and-statement-can-be-made-that-applies-equally-to-all-flows-that-can-be-supported-by-the-forwardingentity
note-that-if-validation-is-relevant-but-consistent-statement-cannot-be-made-then-the-forwardingentity-should-be-described-in-terms-of-subordinate-parts-against-which-coherent-statements-can-be-made
note-that-validation-may-not-be-possible-for-the-specific-layer-protocol-or-in-the-particular-case;
                        uses validation-pac;
                        description    
                "none";
                    }
                    list layer-transition-pac {
                        if-feature present-if-layer-transition-information-is-relevant-to-usage-and-statement-can-be-made-that-applies-equally-to-all-flows-that-can-be-supported-by-the-forwardingentity
note-that-if-layer-transition-is-relevant-but-consistent-statement-cannot-be-made-then-the-forwardingentity-should-be-described-in-terms-of-subordinate-parts-against-which-coherent-statements-can-be-made
note-that-layer-transition-occurs-in-a-limited-number-of-cases;
                        uses layer-protocol-transition-pac;
                        description    
                "none";
                    }
                    description    
                "A ForwardingEntity is an abstract representation of the emergent effect of the combined functioning of an arrangement of components (running hardware, software running on hardware etc.). 
                        The effect can be considered as the realization of the potential for apparent communication adjacency for entities that are bound to the terminations at the boundary of the ForwardingEntity.
                        The ForwardingEntity enables the creation of constrained forwarding to achieve the apparent adjacency.
                        The apparent adjacency has intended performance degraded from perfect adjacency and a statement of that degradation is conveyed via the attributes of the packages associated with this class.";
                }
                grouping validation-pac {
                    list validation-mechanism {
                        min-elements 1;
                        uses validation-mechanism;
                        description    
                "Provides details of the specific validation mechanism(s) used to confirm the presence of an intended ForwardingEntity.";
                    }
                    description    
                "Validation covers the various adjacency discovery and reachability verification protocols. Also may cover Information source and degree of integrity.";
                }
                feature present-if-jittercharacteristic-information-is-relevant-to-usage-and-statement-can-be-made-that-applies-equally-to-all-flows-that-can-be-supported-by-the-forwardingentity
note-that-if-jittercharacteristic-is-relevant-but-consistent-statement-cannot-be-made-then-the-forwardingentity-should-be-described-in-terms-of-subordinate-parts-against-which-coherent-statements-can-be-made
note-that-this-only-applies-to-tdm {
                description    
                none;
                }
                feature present-if-wandercharacteristic-information-is-relevant-to-usage-and-statement-can-be-made-that-applies-equally-to-all-flows-that-can-be-supported-by-the-forwardingentity
note-that-if-wandercharacteristic-is-relevant-but-consistent-statement-cannot-be-made-then-the-forwardingentity-should-be-described-in-terms-of-subordinate-parts-against-which-coherent-statements-can-be-made
note-that-this-only-applies-to-tdm {
                description    
                none;
                }
                feature present-if-queuinglatencycharacteristic-information-is-relevant-to-usage-and-statement-can-be-made-that-applies-equally-to-all-flows-that-can-be-supported-by-the-forwardingentity
there-may-be-more-than-one-instance-if-the-queuing-behavior-depends-upon-traffic-properties
note-that-if-queuinglatencycharacteristic-is-relevant-but-consistent-statement-cannot-be-made-then-the-forwardingentity-should-be-described-in-terms-of-subordinate-parts-against-which-coherent-statements-can-be-made
note-that-this-only-applies-to-packet-system {
                description    
                none;
                }
                feature present-if-errorcharacteristic-information-is-relevant-to-usage-and-statement-can-be-made-that-applies-equally-to-all-flows-that-can-be-supported-by-the-forwardingentity
note-that-if-errorcharacteristic-is-relevant-but-consistent-statement-cannot-be-made-then-the-forwardingentity-should-be-described-in-terms-of-subordinate-parts-against-which-coherent-statements-can-be-made
note-that-this-only-applies-to-tdm {
                description    
                none;
                }
                feature present-if-losscharacteristic-information-is-relevant-to-usage-and-statement-can-be-made-that-applies-equally-to-all-flows-that-can-be-supported-by-the-forwardingentity
note-that-if-losscharacteristic-is-relevant-but-consistent-statement-cannot-be-made-then-the-forwardingentity-should-be-described-in-terms-of-subordinate-parts-against-which-coherent-statements-can-be-made
note-that-this-only-applies-to-packet-systems {
                description    
                none;
                }
                feature present-if-repeatdeliverycharacteristic-information-is-relevant-to-usage-and-statement-can-be-made-that-applies-equally-to-all-flows-that-can-be-supported-by-the-forwardingentity
note-that-if-repeatdeliverycharacteristic-is-relevant-but-consistent-statement-cannot-be-made-then-the-forwardingentity-should-be-described-in-terms-of-subordinate-parts-against-which-coherent-statements-can-be-made
note-that-this-primarily-applies-to-packet-systems-where-a-packet-may-be-delivered-more-than-once-(in-fault-recovery-for-example)
note-that-it-can-also-apply-to-tdm-where-several-frames-may--be-received-twice-due-to-switching-in-a-system-with-a-large-differential-propagation-delay {
                description    
                none;
                }
                feature present-if-deliveryordercharacteristic-information-is-relevant-to-usage-and-statement-can-be-made-that-applies-equally-to-all-flows-that-can-be-supported-by-the-forwardingentity
note-that-if-deliveryordercharacteristic-is-relevant-but-consistent-statement-cannot-be-made-then-the-forwardingentity-should-be-described-in-terms-of-subordinate-parts-against-which-coherent-statements-can-be-made
note-that-this-only-applies-to-packet-systems
 {
                description    
                none;
                }
                feature present-if-serverintegrityprocesscharacteristic-information-is-relevant-to-usage-and-statement-can-be-made-that-applies-equally-to-all-flows-that-can-be-supported-by-the-forwardingentity
note-that-if-serverintegrityprocesscharacteristic-is-relevant-but-consistent-statement-cannot-be-made-then-the-forwardingentity-should-be-described-in-terms-of-subordinate-parts-against-which-coherent-statements-can-be-made
note-that-this-only-applies-where-the-server-has-some-error-recovery-mechanism-alters-the-characteristics-of-the-link-from-a-normal-distribution {
                description    
                none;
                }
                feature present-if-risk-information-is-relevant-to-usage-and-statement-can-be-made-that-applies-equally-to-all-flows-that-can-be-supported-by-the-forwardingentity
note-that-if-risk-is-relevant-but-consistent-statement-cannot-be-made-then-the-forwardingentity-should-be-described-in-terms-of-subordinate-parts-against-which-coherent-statements-can-be-made {
                description    
                none;
                }
                feature present-if-cost-information-is-relevant-to-usage-and-statement-can-be-made-that-applies-equally-to-all-flows-that-can-be-supported-by-the-forwardingentity
note-that-if-cost-is-relevant-but-consistent-statement-cannot-be-made-then-the-forwardingentity-should-be-described-in-terms-of-subordinate-parts-against-which-coherent-statements-can-be-made {
                description    
                none;
                }
                feature present-if-transfer-timing-information-is-relevant-to-usage-and-statement-can-be-made-that-applies-equally-to-all-flows-that-can-be-supported-by-the-forwardingentity
note-that-if-transfer-timing-is-relevant-but-consistent-statement-cannot-be-made-then-the-forwardingentity-should-be-described-in-terms-of-subordinate-parts-against-which-coherent-statements-can-be-made {
                description    
                none;
                }
                feature present-if-transfer-capacity-information-is-relevant-to-usage-and-statement-can-be-made-that-applies-equally-to-all-flows-that-can-be-supported-by-the-forwardingentity
note-that-if-transfer-capacity-is-relevant-but-consistent-statement-cannot-be-made-then-the-forwardingentity-should-be-described-in-terms-of-subordinate-parts-against-which-coherent-statements-can-be-made {
                description    
                none;
                }
                feature present-if-transfer-integrity-information-is-relevant-to-usage-and-statement-can-be-made-that-applies-equally-to-all-flows-that-can-be-supported-by-the-forwardingentity
note-that-if-transfer-integrity-is-relevant-but-consistent-statement-cannot-be-made-then-the-forwardingentity-should-be-described-in-terms-of-subordinate-parts-against-which-coherent-statements-can-be-made {
                description    
                none;
                }
                feature present-if-validation-information-is-relevant-to-usage-and-statement-can-be-made-that-applies-equally-to-all-flows-that-can-be-supported-by-the-forwardingentity
note-that-if-validation-is-relevant-but-consistent-statement-cannot-be-made-then-the-forwardingentity-should-be-described-in-terms-of-subordinate-parts-against-which-coherent-statements-can-be-made
note-that-validation-may-not-be-possible-for-the-specific-layer-protocol-or-in-the-particular-case {
                description    
                none;
                }
                feature present-if-layer-transition-information-is-relevant-to-usage-and-statement-can-be-made-that-applies-equally-to-all-flows-that-can-be-supported-by-the-forwardingentity
note-that-if-layer-transition-is-relevant-but-consistent-statement-cannot-be-made-then-the-forwardingentity-should-be-described-in-terms-of-subordinate-parts-against-which-coherent-statements-can-be-made
note-that-layer-transition-occurs-in-a-limited-number-of-cases {
                description    
                none;
                }

            /****************************************
            * package resilience
            **************************************/ 
                grouping configuration-and-switch-control {
                    leaf switch-rule {
                        type to-be-defined;
                        description    
                    "A sketch of the presence of complex rules governing the switch behavior.";
                    }
                    list fc-switch {
                        uses fc-switch;
                        description    
                "The switch being controlled.";
                    }
                    container control-parameters {
                        uses control-parameters-pac;
                        description    
                "The control parameters to be applied if local parameters are used rather than profiles.";
                    }
                    list profile-proxy {
                        uses profile-proxy;
                        description    
                "Applied profiles.";
                    }
                    container local-pac {
                        uses local-pac;
                        description    
                "none";
                    }
                    container global-pac {
                        uses global-pac;
                        description    
                "none";
                    }
                    leaf is-frozen {
                        type boolean;
                        default "false";
                        description    
                    "Temporarily prevents any switch action to be taken and, as such, freezes the current state. 
                            Until the freeze is cleared, additional near-end external commands are rejected and fault condition changes and received APS messages are ignored.
                            All administrative controls of any aspect of protection are rejected.";
                    }
                    leaf is-coordinated-switching-both-ends {
                        type boolean;
                        default "false";
                        description    
                    "The C&SC is operating such that switching at both ends of each flow across the FC is coordinated at both ingress and egress ends.";
                    }
                    leaf-list subordinate-control {
                        type leafref {
                            pathmust "/core-model:network-control-domain/core-model:network-element/core-model:ltp/core-model:embedded-clock/core-model:encapsulated-fc/core-model:configuration-and-switch-control/core-model:";
                    require-instance false;
                        }
                must  'deref(.) = current()';
                        description     
                 "A C&SC that is fully or partially subordinate this C&SC. 
                            A peer is considered as partially subordinate in that the peer will respond to requests for action from this C&SC but will also make requests for action to be carried out by this C&SC.
                            Where there is a peer relationship each controller in the peering will see the other controller as subordinate.";
                    }
                    container casc-spec {
                        uses configuration-and-switch-controller-spec;
                        description    
                "none";
                    }
                    leaf-list encapsulated-casc {
                        type leafref {
                            pathmust "/core-model:network-control-domain/core-model:network-element/core-model:ltp/core-model:embedded-clock/core-model:encapsulated-fc/core-model:configuration-and-switch-control/core-model:";
                    require-instance false;
                        }
                must  'deref(.) = current()';
                        description     
                 "Where a C&SC is complex it may be decomposed into subordinate C&SC parts.
                            The decomposition is described by the C&SC spec.";
                    }
                    list casc-port {
                        uses casc-port;
                        description    
                "A reference to ports of a C&SC that can be used where there is significant asymmetry to be represented.
                            The C&SC need not have ports.";
                    }
                    list coordinated-fc {
                        uses forwarding-construct;
                        description    
                "none";
                    }
                    leaf resilience-control-status {
                        type resilience-control;
                        description    
                    "The state of the control process.";
                    }
                    description    
                "Represents the capability to control and coordinate switches, to add/delete/modify FCs and to add/delete/modify LTPs/LPs so as to realize a protection scheme.";
                }
                grouping control-parameters-pac {
                    leaf reversion-mode {
                        type reversion-mode;
                        description    
                    "Indicates whether the protection scheme is revertive or non-revertive.";
                    }
                    leaf wait-to-revert-time {
                type int64;
                        default "15";
                        description    
                    "If the protection system is revertive, this attribute specifies the time, in minutes, to wait after a fault clears on a higher priority (preferred) resource before switching to the preferred resource.
                            If a further fault occurs on the preferred resource in the waitToRevertTime then the reversion attempt is cancelled.
                            The WTR timer is overridden by the needs of a higher priority signal. Depending upon which resource is requested this may simply cancel the attempt to revert of may cause immediate reversion.";
                    }
                    leaf prot-type {
                        type protection-type;
                        description    
                    "Indicates the protection scheme that is used for the ProtectionGroup.";
                    }
                    leaf hold-off-time {
                type int64;
                        description    
                    "This attribute indicates the time, in milliseconds, between declaration of a switch trigger condition (e.g. signal degrade or signal fail), and the initialization of the protection switching algorithm.";
                    }
                    container network-scheme-specification {
                        uses network-scheme-specification;
                        description    
                "none";
                    }
                    description    
                "A list of control parameters to apply to a switch.";
                }
                grouping fc-route {
                    leaf-list fc {
                        type leafref {
                            pathmust "/core-model:network-control-domain/core-model:network-element/core-model:ltp/core-model:embedded-clock/core-model:encapsulated-fc/core-model:";
                    require-instance false;
                        }
                must  'deref(.) = current()';
                        description     
                 "The list of FCs describing the route of an FC.
                            In most cases the FcRoute has 2 or more FCs however there are some cases where a Route with one FC is valid.";
                    }
                    leaf selection-priority {
                type int64;
                        default "0";
                        description    
                    "The preference priority of the resource in the resilience scheme for a particular FC. 
                            The lower the value the higher the priority.
                            A lower value of selection priority is preferred
                            If two resources have the same value they are of equal priority.
                            There is no preference between equal priorities.
                            If a resource with the lowest value selection priority fails, then the next lowest value available (may be the same value) is picked.
Hence on failure of the current resource the next best available will be selected.
                            If there are several equal values, the choice is essentially arbitrary).
                            If the scheme is revertive then when a resource of higher priority than the currently selected resource recovers it will be selected.
                            This is equivalent to working/protection but allows for all static scheme types with n:m capability. 
                            In simple schemes 0 = working and 1 = protecting.
                            If selection priority of a Route is increased in value and the Route is currently selecting this Route, then if another Route of a lower selection priority value is available the wait to restore process will come into action as if the other Route had just become available.
                            If selection priority of a Route is changed and the FC is not currently selecting this Route but is selecting an item that is now of a higher numeric value than the changed Route, then the wait to restore process will come into action as if the other Route had just become available.";
                    }
                    leaf route-selection-control {
                        type route-selection-control;
                        default "SWITCH_CONTROL_NORMAL";
                        description    
                    "Degree of administrative control applied to the route selection.";
                    }
                    leaf route-selection-reason {
                        type route-selection-reason;
                        config false;
                        description    
                    "The reason for the current route selection.";
                    }
                    leaf-list link {
                        type leafref {
                            pathmust "/core-model:link/core-model:";
                    require-instance false;
                        }
                must  'deref(.) = current()';
                        description     
                 "none";
                    }
                    uses global-class;
                    description    
                "Each instance of an FC Route (FcRoute) class models an individual route of an FC. The route is an alternative view of the internal structure of the FC to FC aggregation (see FcHasLowerLeverFcs association).
                        There are cases where a route is the most appropriate representation and cases where the aggregation approach is the most appropriate representation.
                        The route of an FC object is represented by a list of FCs at a lower level with the implicit understanding that unmodeled link connections are interleaved between the lower level FCs. 
                        Note that depending on the service supported by an FC, the FC can have multiple routes.
                        The FcRoute is also applicable where an NE level ForwardingDomain may be decomposed into subordinate ForwardingDomains. Applies to both virtual and real NE cases.";
                }
                grouping fc-switch {
                    leaf hold-off-time {
                type int64;
                        description    
                    "Moved to ControlParameter_Pac. This attribute indicates the time, in seconds, between declaration of unacceptable quality of signal on the currently selected FcPort, and the initialization of the protection switching algorithm. ";
                    }
                    leaf prot-type {
                        type protection-type;
                        description    
                    "Indicates the protection scheme that is used for the ProtectionGroup.";
                    }
                    leaf reversion-mode {
                        type reversion-mode;
                        default "REVERSION_MODE_REVERTIVE";
                        description    
                    "Moved to ControlParameter_Pac. This attribute whether or not the protection scheme is revertive or non-revertive. ";
                    }
                    list selected-fc-port {
                        uses fc-port;
                        description    
                "Indicates which points are selected by the switch.
                            Depending on the switch spec (via FcSpec)
                            - more than one FcPort can be selected at any one time (e.g. egress switch, ingress packet switch)
                            - zero FcPorts can be selected. For an ingress switch this indicates that the switch common (egress) is 'high impedance'
.";
                    }
                    list profile-proxy {
                        uses profile-proxy;
                        description    
                "Provides a set of predefined values for switch control in place of the direct values available via the FcSwitch or via _configurationAndSwitchControl.";
                    }
                    container configuration-and-switch-control {
                        uses configuration-and-switch-control;
                        description    
                "A ConfigurationAndSwitchController that is external to the switch (it is coordinating many switches and hence cannot be encapsulated in the FcSwitch.";
                    }
                    container internal-configuration-and-switch-control {
                        uses configuration-and-switch-control;
                        description    
                "A ConfigurationAndSwitchController encapsulated in the FcSwitch that controls the FcSwitch alone.";
                    }
                    leaf switch-control {
                        type switch-control;
                        default "SWITCH_CONTROL_NORMAL";
                        description    
                    "Degree of administrative control applied to the switch selection.";
                    }
                    leaf switch-selects-ports {
                        type port-direction;
                        default "PORT_DIRECTION_INPUT";
                        description    
                    "Indicates whether the switch selects from ingress to the FC or to egress of the FC, or both.";
                    }
                    leaf switch-selection-reason {
                        type switch-state-reason;
                        config false;
                        description    
                    "The reason for the current switch selection.";
                    }
                    container control-parameters {
                        uses control-parameters-pac;
                        description    
                "none";
                    }
                    leaf wait-to-restore-time {
                type int64;
                        description    
                    "Moved to ControlParameter_Pac and changed to waitToRevert. If the protection system is revertive, this attribute specifies the amount of time, in seconds, to wait after the preferred FcPort returns to an acceptable state of operation (e.g. a fault has cleared) before restoring traffic to that preferred FcPort.";
                    }
                    uses local-class;
                    description    
                "The FcSwitch class models the switched forwarding of traffic (traffic flow) between FcPorts and is present where there is protection functionality in the FC. 
                        If an FC exposes protection (having two or more FcPorts that provide alternative identical inputs/outputs), the FC will have one or more associated FcSwitch objects to represent the alternative flow choices visible at the edge of the FC.
                        The FC switch represents and defines a protection switch structure encapsulated in the FC and essentially 'decorates' FCs that are involved in resilience schemes that use switching in a protection mechanism. 
                        Essentially FcSwitch performs one of the functions of the Protection Group in a traditional model. It associates 2 or more FcPorts each playing the role of a Protection Unit. 
                        One or more protection, i.e. standby/backup, FcPorts provide protection for one or more working (i.e. regular/main/preferred) FcPorts where either protection or working can feed one or more protected FcPort.
                        The switch may be used in revertive or non-revertive (symmetric) mode. When in revertive mode it may define a waitToRestore time.
                        It may be used in one of several modes including source switched, destination switched, source and destination switched etc. (covering cases such as 1+1 and 1:1).
                        It may be locked out (prevented from switching), force switched or manual switched.
                        It will indicate switch state and change of state.
                        The switch can be switched away from all sources such that it becomes open and hence two coordinated switches can both feed the same LTP so long as at least one of the two is switched away from all sources (is 'open').
                        The ability for a Switch to be 'high impedance' allows bidirectional ForwardingConstructs to be overlaid on the same bidirectional LTP where the appropriate control is enabled to prevent signal conflict.
                        This ability allows multiple alternate routes to be present that otherwise would be in conflict.";
                }
                grouping casc-port {
                    leaf port-role {
                        type string;
                        description    
                    "The role of the port of a C&SC. 
                            The interpretation of the role is provided by the C&SC spec.
                            The C&SC spec will set out the role in the context of C&SC functions.
                            The role will indicate how the port relates to the associated entity, e.g. is conveying messages.";
                    }
                    container port-role-properties {
                        uses casc-port-role-properties;
                        description    
                "A link to properties associated with the port role as defined by the CascSpec.";
                    }
                    list ltp {
                        uses logical-termination-point;
                        description    
                "The LTP that conveys the messages related to the port and/or is subject to control action and/or provides indications of state etc.
                            For direct association, there may be up to 2 LTPs (to account for directionality differences).
                            In the specification representation, there may be a number rules that provide further LTP relationships that are implicit in the instantiated model.";
                    }
                    leaf encapsulating-casc-port {
                        type leafref {
                            pathmust "/core-model:network-control-domain/core-model:network-element/core-model:ltp/core-model:embedded-clock/core-model:encapsulated-fc/core-model:configuration-and-switch-control/core-model:casc-port/core-model:";
                    require-instance false;
                        }
                must  'deref(.) = current()';
                        description    
                    "In a case where there is nested C&SC the ports are also nested and this references the superior port.";
                    }
                    leaf is-related-control-flow-disabled {
                        type boolean;
                        default "true";
                        description    
                    "If TRUE, then any Control signal flow related to this controller (to, from or drop-and-continue) is prevented from passing through the related LTP carrying the signaling for this controller.
                            This can be considered as being realized using an FcSwitch in an FC embedded in the LP at the layer of signaling to disconnect the FcPort bidirectionally.
                            This FcSwitch should be represented in the LTP spec.
                            Note that the FcSwitch will be at the granularity of the relevant control signal and other flows may be passed uninterrupted.";
                    }
                    leaf is-controlled-fc-port-disabled {
                        type boolean;
                        default "false";
                        description    
                    "If TRUE, then the related FcPort on the FC is disabled and hence signal will not flow through that FcPort.
                            This is realized using an FcSwitch to disconnect the FcPort bidirectionally.
                            Note that as the controller may control many FCs and may switch them all together as one, in an implementation the FcSwitch could be omitted from the FC instance model.
                            Any omission should be explained by the FcSpec.
                            This is equivalent to a blocked indication on the LTP used in other representations.";
                    }
                    leaf is-protection-lock-out {
                        type boolean;
                        default "false";
                        description    
                    "The resource is configured to temporarily not be available for use in the protection scheme(s) it is part of.
                            This overrides all other protection control states including forced.
                            If the item is locked out, then it cannot be used under any circumstances.
                            This causes isRelatedControlFlowDisabled to become TRUE and isControlledFcPortDisabled to become TRUE.";
                    }
                    description    
                "A port of a C&SC that can be used where there is significant asymmetry to be represented.
                        This can represent any combination of:
                        - the conveying of messaging to/from the C&SC
                        - the conveying of control action
                        - the providing of indications of state etc.";
                }
                grouping casc-port-role-properties {
                    leaf signalling-format {
                        type string;
                        description    
                    "A reference to the definition of the signalling format used by the instance referenced by the related port.
                            This is a placeholder for a more sophisticated capability.";
                    }
                    leaf monitoring-details {
                        type string;
                        description    
                    "Information on what is being monitored in the instance referenced by the related port.
                            This is a placeholder for a more sophisticated capability.";
                    }
                    leaf control-details {
                        type string;
                        description    
                    "Information on what is being controlled in the instance referenced by the related port.
                            This is a placeholder for a more sophisticated capability.";
                    }
                    description    
                " Container for properties associated with the port role as defined by the CascSpec.";
                }

            /****************************************
            * package timing
            **************************************/ 
                grouping clock {
                    leaf run-mode {
                        type run-mode;
                        config false;
                        description    
                    "The run-mode of the frequency system clock, such as free-run, locked, and holdover.";
                    }
                    leaf-list encompassed-clock {
                        type leafref {
                            path "/core-model:network-control-domain/core-model:network-element/core-model:ltp/core-model:embedded-clock/core-model:";
                    require-instance false;
                        }
                        description     
                 "A clock may be emergent from and may effectively encompass several clocks in a resilient solution.";
                    }
                    list encapsulated-fc {
                        uses forwarding-construct;
                        description    
                "A Clock may encapsulate an FC related to resilience where the clock provides an output that is essentially that of one of several other clocks in the resilience scheme.";
                    }
                    leaf-list sync-ltp {
                        type leafref {
                            pathmust "/core-model:network-control-domain/core-model:network-element/core-model:ltp/core-model:";
                    require-instance false;
                        }
                must  'deref(.) = current()';
                        description     
                 "A clock may feed one or more LTPs with timing information to propagate across the network (it may feed no LTPs).";
                    }
                    list encapsulated-casc {
                        uses configuration-and-switch-control;
                        description    
                "The clock may encapsulate a complex FC where there is a resilience mechanism active and that FC will need to be controlled. 
                            The Casc to control the FC can be encapsulated in the Clock.";
                    }
                    leaf-list phase-aligned-clock {
                        type leafref {
                            path "/core-model:network-control-domain/core-model:network-element/core-model:ltp/core-model:embedded-clock/core-model:";
                    require-instance false;
                        }
                        description     
                 "One or more clocks can be actively phase aligned (this is especially relevant in a hitless resilience scheme).";
                    }
                    uses local-class;
                    description    
                "Clock function processes the input sync information (frequency and ssm or time stamp and PTP announce messages) and provides the modified sync information to the sync distribution function.
                        If none of the inputs meet the quality defined by the controller the clock may enter a hold-over or free run mode. 
                        The status of the clock will be reported to the controller.";
                }

            grouping forwarding-domain {
                list layer-protocol-name {
                    min-elements 1;
                    uses layer-protocol-name-and-qualifier;
                    description    
                "One or more protocol layers at which the FD represents the opportunity to enable forwarding between LTP that bound it.";
                }
                leaf-list lower-level-fd {
                    type leafref {
                        pathmust "/core-model:network-control-domain/core-model:network-element/core-model:fd/core-model:";
                    require-instance false;
                    }
                must  'deref(.) = current()';
                    description     
                 "The FD class supports a recursive aggregation relationship (HigherLevelFdEncompassesLowerLevelFds) such that the internal construction of an FD can be exposed as multiple lower level FDs and associated Links (partitioning).
                        The aggregated FDs and Links form an interconnected topology that provides and describes the capability of the aggregating FD.
                        Note that the model actually represents an aggregation of lower level FDs into higher level FDs as views rather than FD partition, and supports multiple views. 
                        Aggregation allow reallocation of capacity from lower level FDs to different higher level FDs as if the network is reorganized (as the association is aggregation not composition).";
                }
                list fc {
                    uses forwarding-construct;
                    description    
                "An FD aggregates one or more FCs. An aggregated FC connects LTPs that bound the FD.";
                }
                leaf-list ltp {
                    type leafref {
                        pathmust "/core-model:network-control-domain/core-model:network-element/core-model:ltp/core-model:";
                    require-instance false;
                    }
                must  'deref(.) = current()';
                    description     
                 "An instance of FD is associated with zero or more LTP objects. 
                        The LTPs that bound the FD provide capacity for forwarding.
                        For asymmetric FDs, the association to the LTP is via the FdPort.";
                }
                leaf-list lower-level-link {
                    type leafref {
                        pathmust "/core-model:link/core-model:";
                    require-instance false;
                    }
                must  'deref(.) = current()';
                    description     
                 "The FD encompasses Links that interconnect lower level FDs and collect Links that are wholly within the bounds of the FD.
                        See also _lowerLevelFd.";
                }
                leaf fd-rule-set {
                    type leafref {
                        pathmust "/core-model:fd-and-link-rule-set/core-model:";
                    require-instance false;
                    }
                must  'deref(.) = current()';
                    description    
                    "The rules related to an FD.";
                }
                leaf-list fd-spec {
                    type leafref {
                        pathmust "/core-model:network-control-domain/core-model:network-element/core-model:fd/core-model:";
                    require-instance false;
                    }
                must  'deref(.) = current()';
                    description     
                 "none";
                }
                list fd-port {
                    uses fd-port;
                    description    
                "The association of the FD to LTPs is either made directly for symmetric FDs or via FdPort for asymmetric FDs.";
                }
                uses global-class;
                uses forwarding-entity;
                description    
                "The ForwardingDomain (FD) class models the topological component that represents a forwarding capability that provides the opportunity to enable forwarding (of specific transport characteristic information at one or more protocol layers) between points.
                    The FD object provides the context for and constrains the formation, adjustment and removal of FCs and hence offers the potential to enable forwarding.
                    The FCs may be formed between LTPs at the boundary of the FD or between AccessPorts at the boundary of the FD (for the most basic media layers cases - most media cases use LTPs).
                    A number of FDs (related by Links) may be grouped and abstracted to form an FD where that FD represents the effect of the underlying FDs but where the detailed structure is not apparent.
                    This grouping and abstraction is potentially recursive. 
                    This aspect is essentially equivalent to ITU-T partitioning but this is an aggregation not a composition, so it allows an FD to be in multiple higher level FDs.
                    The notion of abstraction/grouping assumes that small things are brought together into larger things as opposed to ITU-T partitioning that assumes large things are broken down into smaller things.
                    An FD represents an abstraction of some combination of software behavior, electronic behavior and physical structure that provides a forwarding capability. 
                    At a lower level of recursion an FD could represent a forwarding capability within a device. 
                    A device may encompass two or more disjoint forwarding capabilities and may support more than one layer protocol, hence more than one FD.
                    A routing fabric may be logically partitioned to represent connectivity constraints, hence the FD representing the routing fabric may be partitioned into a number of FDs representing the constraints.
                    The FD represents a subnetwork [ITU-T G.800], FlowDomain [TMF 612] and a MultiLayerSubNetwork (MLSN) [TMF 612]. 
                    As in the TMF concept of MLSN the FD can support more than one layer-protocol.
                    Note that the ITU-T G.800 subnetwork is a single layer entity.";
            }
            grouping forwarding-construct {
                container layer-protocol-name {
                    uses layer-protocol-name-and-qualifier;
                    description    
                "The layerProtocol at which the FC enables the potential for forwarding.";
                }
                leaf-list lower-level-fc {
                    type leafref {
                        pathmust "/core-model:network-control-domain/core-model:network-element/core-model:ltp/core-model:embedded-clock/core-model:encapsulated-fc/core-model:";
                    require-instance false;
                    }
                must  'deref(.) = current()';
                    description     
                 "An FC object supports a recursive aggregation relationship such that the internal construction of an FC can be exposed as multiple lower level FC objects (partitioning).
                        Aggregation is used as for the FD to allow changes in hierarchy. 
                        FC aggregation reflects FD aggregation. 
                        For example a low level FC could represent what would have traditionally been considered as a 'Cross-Connection' in an 'NE'. The 'Cross-Connection' in an 'NE' is not necessarily the lowest level of FC partitioning.
                        ";
                }
                leaf-list fc-route {
                    type leafref {
                        pathmust "/core-model:fc-route/core-model:";
                    require-instance false;
                    }
                must  'deref(.) = current()';
                    description     
                 "An FC object can have zero or more routes, each of which is defined as a list of lower level FC objects describing the flow across the network.";
                }
                list fc-port {
                    min-elements 2;
                    uses fc-port;
                    description    
                "The FcPorts define the boundary of the FC.
                        The FC is accessed via the FcPorts.
                        Flow within the FC is defined in terms of its FcPorts.";
                }
                list fc-switch {
                    uses fc-switch;
                    description    
                "If an FC exposes protection (having two FcPorts that provide alternative identical inputs/outputs), the FC will have one or more associated FcSwitch objects.
                        The arrangement of switches for a particular instance is described by a referenced FcSpec.";
                }
                list configuration-and-switch-control {
                    uses configuration-and-switch-control;
                    description    
                "Reference to a ConfigurationAndSwitchController that coordinates switches encapsulated in the FC.
                        The controller coordinates multiple switches in the same FC.";
                }
                leaf forwarding-direction {
                    type forwarding-direction;
                    description    
                    "The directionality of the ForwardingConstruct. 
                        Is applicable to simple ForwardingConstructs where all FcPorts are BIDIRECTIONAL (the ForwardingConstruct will be BIDIRECTIONAL) or UNIDIRECTIONAL (the ForwardingConstruct will be UNIDIRECTIONAL). 
                        Is not present in more complex cases.
                        In the case of media the FcPorts and FC may also be omni-directional.";
                }
                leaf is-protection-lock-out {
                    if-feature in-protection-context-if-server-of-protection-where-entire-server-is-to-be-excluded-from-use-for-protection;
                    type boolean;
                    default "false";
                    description    
                    "The resource is configured to temporarily not be available for use in the protection scheme(s) it is part of.
                        This overrides all other protection control states including forced.
                        If the item is locked out then it cannot be used under any circumstances.
                        Note: Only relevant when part of a protection scheme.";
                }
                leaf service-priority {
                type int64;
                    default "0";
                    description    
                    "Relevant where 'service' FCs are competing for server resources.
                        Used to determine which signal FC is allocated resource. 
                        The priority of the 'service' with respect to other 'services'. 
                        Lower numeric value means higher priority. 
                        Covers cases such as pre-emptible in a resilience solution. ";
                }
                list fc-spec-reference-class-ref {
                    if-feature spectargetclass-forwardingconstruct;
                    min-elements 1;
                    uses metaclass-class;
                    description    
                "Reference to the specific FcSpec class that defines the properties that augment the instance of FC.";
                }
                list supported-link {
                    uses link;
                    description    
                "An FC that spans between LTPs that terminate the LayerProtocol usually supports one or more links in the client layer.";
                }
                list multiple-strand-span {
                    uses multiple-strand-span;
                    description    
                "none";
                }
                container supporting-pc {
                    uses processing-construct;
                    description    
                "The functionality supporting this entity.";
                }
                uses global-class;
                uses forwarding-entity;
                description    
                "The ForwardingConstruct (FC) represents enabled constrained potential for forwarding between two or more FcPorts at a particular specific layerProtocol .
                    The constraint is explained by the FcSpec. Even when an FC is in place enabling potential for flow, it is possible that no information is flowing as there is no flow matching the constraint, hence 'potential'.
                    Like the LTP, the FC supports any transport protocol including all analogue, circuit and packet forms.
                    The FC is used to effect forwarding of transport characteristic (layer protocol) information.
                    An FC can be in only one ForwardingDomain (FD).
                    The FC is a forwarding entity.
                    At a low level of the recursion, a FC represents a cross-connection within an NE. It may also represent a fragment of a cross-connection under certain circumstances.
                    The FC object can be used to represent many different structures including point-to-point (P2P), point-to-multipoint (P2MP), rooted-multipoint (RMP) and multipoint-to-multipoint (MP2MP) bridge and selector structures for linear, ring or mesh protection schemes.
                    When applied to media, the FC represents the ability for a flow/wave (potentially containing information), to be propagated between FcPorts. 
                    The existence of a FC instance is independent of the presence (or absence) of a flow/wave (and any information encoded within it) where flow/wave covers the progressing of any analogue or digital (packet/frame etc.) structure.
                    A flow/wave cannot propagate in the absence of a FC instance.";
            }
            grouping network-control-domain {
                leaf-list fd {
                    type leafref {
                        pathmust "/core-model:network-control-domain/core-model:network-element/core-model:fd/core-model:";
                    require-instance false;
                    }
                must  'deref(.) = current()';
                    description     
                 "The FDs accessible via the NCD.";
                }
                leaf-list link {
                    type leafref {
                        pathmust "/core-model:link/core-model:";
                    require-instance false;
                    }
                must  'deref(.) = current()';
                    description     
                 "The links accessible in the scope of the NCD. 
                        The domain is bounded by off-network links.";
                }
                list network-element {
                    uses network-element;
                    description    
                "The network elements within the scope of the NCD where each NE is within one and only one domain.";
                }
                uses global-class;
                description    
                "The Network Control Domain (NCD) class represents the scope of control that a particular SDN controller has with respect to a particular network, (i.e., encompassing a designated set of interconnected network elements).
                    In the interfaces between SDN controllers where virtualization is necessary, e.g., in client/server SDN controller relationship, the NCD object defines the scope of control of the client SDN controller on the virtual network that has been provided by the server SDN controller (i.e., the scope of control relates to the partitioned provider resources allocated to that particular client). 
                    The NCD provides the scope of naming space for identifying objects representing the virtual resources within the virtual network.";
            }
            grouping link {
                list layer-protocol-name {
                    min-elements 1;
                    uses layer-protocol-name-and-qualifier;
                    description    
                "The Link can support multiple transport layer protocols via the associated LTP object. 
                        For implementation optimization, where appropriate, multiple layer-specific Links can be merged and represented as a single Link instance as the Link can represent a list of layer protocols.
                        A Link may support different layer protocols at each of its LinkPorts when it is a transitional Link.";
                }
                list fd {
                    min-elements 2;
                    uses forwarding-domain;
                    description    
                "The Link associates with two or more FDs. 
                        This association provides a direct summarization of the association via LinkPort and LTP.";
                }
                list link-port {
                    min-elements 2;
                    uses link-port;
                    description    
                "The association of the Link to LTPs is made via LinkPort (essentially the ports of the Link).";
                }
                leaf-list lower-level-link {
                    type leafref {
                        pathmust "/core-model:link/core-model:";
                    require-instance false;
                    }
                must  'deref(.) = current()';
                    description     
                 "A Link may be formed from subordinate links (similar FD formations from subordinate FDs). This association is intended to cover concepts such as serial compound links. ";
                }
                leaf link-direction {
                    type forwarding-direction;
                    description    
                    "The directionality of the Link. 
                        Is applicable to simple Links where all LinkPorts are BIDIRECTIONAL (the Link will be BIDIRECTIONAL) or UNIDIRECTIONAL (the Link will be UNIDIRECTIONAL). 
                        Is not present in more complex cases.";
                }
                leaf fd-rule-set {
                    type leafref {
                        pathmust "/core-model:fd-and-link-rule-set/core-model:";
                    require-instance false;
                    }
                must  'deref(.) = current()';
                    description    
                    "The rules related to a Link.";
                }
                leaf is-protection-lock-out {
                    if-feature in-protection-context-if-server-of-protection-where-entire-server-is-to-be-excluded-from-use-for-protection;
                    type boolean;
                    default "false";
                    description    
                    "The resource is configured to temporarily not be available for use in the protection scheme(s) it is part of.
                        This overrides all other protection control states including forced.
                        If the item is locked out, then it cannot be used under any circumstances.
                        Note: Only relevant when part of a protection scheme.";
                }
                leaf-list fc {
                    type leafref {
                        pathmust "/core-model:network-control-domain/core-model:network-element/core-model:ltp/core-model:embedded-clock/core-model:encapsulated-fc/core-model:";
                    require-instance false;
                    }
                must  'deref(.) = current()';
                    description     
                 "A Link contains one or more FCs. A contained FC connects LTPs that bound the Link. 
                        This FC represents the traditional link connection. It is often not supported in implementations as it can be inferred from FCs in the corresponding FDs.";
                }
                leaf-list lower-level-fd {
                    type leafref {
                        pathmust "/core-model:network-control-domain/core-model:network-element/core-model:fd/core-model:";
                    require-instance false;
                    }
                must  'deref(.) = current()';
                    description     
                 "FD(s) that form part of a serial compound Link.";
                }
                leaf link-spec {
                    type leafref {
                        pathmust "/core-model:link/core-model:";
                    require-instance false;
                    }
                must  'deref(.) = current()';
                    description    
                    "none";
                }
                list link-spec-reference-class-ref {
                    if-feature spectargetclass-link;
                    min-elements 1;
                    uses metaclass-class;
                    description    
                "none";
                }
                uses global-class;
                uses forwarding-entity;
                description    
                "The Link class models effective adjacency between two or more ForwardingDomains (FD). 
                    For digital layer networks, in its basic form (i.e., point-to-point Link) it associates a set of LTP clients on one FD with an equivalent set of LTP clients on another FD. 
                    Like the FC, the Link has ports (LinkPort) which take roles relevant to the constraints on flows offered by the Link (e.g., Root role or leaf role for a Link that has a constrained Tree configuration).
                    The Link is an abstraction of underlying network complexity which may include resilience schemes etc.";
            }
            grouping network-element {
                list fd {
                    uses forwarding-domain;
                    description    
                "Represents the FD that is completely within the boundary of the NE.
                        At a low level of recursion, an FD (within a network element (NE)) represents a switch matrix (i.e., a fabric). 
                        Note that an NE can encompass multiple switch matrices (FDs) and the FD representing the switch matrix can be further partitioned.
                        Where an FD is referenced by the NeEncompassesFd association, any FDs that it encompasses (i.e., that are associated with it by HigherLevelFdEncompassesLowerLevelFds), must also be encompassed by the NE and hence must have the NeEncompassesFd association.
                        ";
                }
                list ltp {
                    uses logical-termination-point;
                    description    
                "An NE has associated LTPs that are at its boundary.
                        The NeEncompassesFd association occurs for FDs that are within the bounds of the NetworkElement definition such that the FD is bounded by LTPs, all of which are on the boundary of the NetworkElement or are within the NetworkElement. 
                        An LTP can be independent of an NE.";
                }
                uses global-class;
                description    
                "The Network Element (NE) class represents a network element (traditional NE) in the data plane.
                    A data plane network element is essentially a consolidation of capabilities that can be viewed and controlled through a 'single' management-control port.
                    In the direct interface from an SDN controller to a network element in the data plane, the NetworkElement object defines the scope of control for the resources within the network element
                    For example internal transfer of user information between the external terminations (ports of the NE), encapsulation, multiplexing/demultiplexing, and OAM functions, etc. 
                    The NetworkElement provides the scope of the naming space for identifying objects representing the resources within the data plane network element.
                    NE is really a product bundling or some view of management scope, management access, session. 
                    The NE is not directly part of topology but brings meaning to the FD context and the LTP context (and hence the links). ";
            }
            grouping sdn-controller {
                uses global-class;
                description    
                "Represents the SDN controller.";
            }
            grouping fc-port {
                leaf-list ltp {
                    type leafref {
                        pathmust "/core-model:network-control-domain/core-model:network-element/core-model:ltp/core-model:";
                    require-instance false;
                    }
                must  'deref(.) = current()';
                    max-elements 2;
                    description     
                 "The FcPort may be associated with more than one LTP when the FcPort is bidirectional and the LTPs are unidirectional.
                        Multiple LTP
                        - Bidirectional FcPort to two Uni-directional LTPs
                        Zero LTP
                        - BreakBeforeMake transition
                        - Planned LTP not yet in place
                        - Off-network LTP referenced through other mechanism.";
                }
                leaf role {
                    type port-role;
                    description    
                    "Each FcPort of the FC has an assigned role (e.g., working, protection, protected, symmetric, hub, spoke, leaf, root) in the context of the FC with respect to the FC function. 
                        The role is fixed by the referenced FcSpec.";
                }
                leaf fc-port-direction {
                    type port-direction;
                    description    
                    "The orientation of the defined flow at the FcPort.";
                }
                leaf is-protection-lock-out {
                    if-feature in-protection-context-where-the-fcport-is-to-be-excluded-from-use-for-protection;
                    type boolean;
                    default "false";
                    description    
                    "The resource is configured to temporarily not be available for use in the protection scheme(s) it is part of.
                        This overrides all other protection control states including forced.
                        If the item is locked out, then it cannot be used under any circumstances.
                        Note: Only relevant when part of a protection scheme.";
                }
                leaf selection-priority {
                type int64;
                    default "0";
                    description    
                    "The preference priority of the resource in the protection scheme for a particular FC. 
                        The lower the value the higher the priority.
                        A lower value of selection priority is preferred
                        If two resources have the same value they are of equal priority.
                        There is no preference between equal priorities.
                        If a resource with the lowest value selection priority fails,, then the next lowest value available (may be the same value) is picked.
                        Hence on failure of the current resource the next best available will be selected.
                        If there are several equal values, the choice is essentially arbitrary.
                        If the scheme is revertive then when a resource of higher priority than the currently selected resource recovers it will be selected.
                        This is equivalent to working/protection but allows for all static scheme types with n:m capability. 
                        In simple schemes 0 = working and 1 = protecting.
                        If selection priority of an FcPort is increased in value and the FC is currently selecting this FcPort then if another FcPort of a lower selection priority value is available, the wait to restore process will come into action as if the other FcPort had just become available.
                        If selection priority of a FcPort is changed and the FC is not currently selecting this FcPort but is selecting an item that is now of a higher numeric value than the changed FcPort then the wait to restore process will come into action as if the other FcPort had just become available.";
                }
                leaf is-internal-port {
                    type boolean;
                    config false;
                    description    
                    "The FcPort is not exposed and cannot have associated LTPs.
                        This form of FcPort is used to enable chaining of FcSwitches or FcRoutes in complex network protection scenarios.";
                }
                list fc-route-feeds-fc-port-egress {
                    uses fc-route;
                    description    
                "Identifies which route(s) currently actively forward to the FcPort to exit the FC to an LTP (or for an internal FcPort to propagate to the next internal switch/route).";
                }
                leaf-list fc-port {
                    type leafref {
                        pathmust "/core-model:network-control-domain/core-model:network-element/core-model:ltp/core-model:embedded-clock/core-model:encapsulated-fc/core-model:fc-port/core-model:";
                    require-instance false;
                    }
                must  'deref(.) = current()';
                    max-elements 2;
                    description     
                 "An FcPort may have a direct association to another FcPort where there is a transition from one domain to another but where there has been no termination.";
                }
                leaf-list port-of-internal-fc {
                    type leafref {
                        pathmust "/core-model:network-control-domain/core-model:network-element/core-model:ltp/core-model:embedded-clock/core-model:encapsulated-fc/core-model:fc-port/core-model:";
                    require-instance false;
                    }
                must  'deref(.) = current()';
                    description     
                 "none";
                }
                container pin {
                    uses pin;
                    description    
                "For media FCs, the name of the pin that terminates the media.";
                }
                uses local-class;
                description    
                "The association of the FC to LTPs is always made via FcPorts.
                    In the case of media the association between FCs is made via their FcPorts and the association of an FC to the physical Pin is made via the FcPort.
                    The FcPort class models the access to the FC function. 
                    The traffic forwarding between the associated FcPorts of the FC depends upon the type of FC and may be associated with FcSwitch object instances.  
                    In cases where there is resilience, the FcPort may convey the resilience role of the access to the FC. 
                    It can represent a protected (resilient/reliable) point or a protecting (unreliable working/main or protection/spare) point.
                    The FcPort replaces the Protection Unit of a traditional protection model (e.g., ITU-T). 
                    The ForwardingConstruct can be considered as a component and the FcPort as a Port on that component.";
            }
            grouping layer-protocol {
                container layer-protocol-name {
                    uses layer-protocol-name-and-qualifier;
                    description    
                "Indicate the specific layer-protocol described by the LayerProtocol entity.";
                }
                leaf configured-client-capacity {
                    type to-be-defined;
                    description    
                    "Provides a summarized view of the client capacity that is configurable for use.
                        Note the client LTP association should provide all necessary detail hence this attribute is questionable.";
                }
                leaf lp-direction {
                    type termination-direction;
                    description    
                    "The overall directionality of the LP. 
                        - A BIDIRECTIONAL LP will have some SINK and/or SOURCE flows.
                        - A SINK LP can only contain elements with SINK flows or CONTRA_DIRECTION_SOURCE flows
                        - A SOURCE LP can only contain SOURCE flows or CONTRA_DIRECTION_SINK flows";
                }
                leaf termination-state {
                    type termination-state;
                    description    
                    "Indicates whether the layer is terminated and if so how.";
                }
                list configuration-and-switch-control {
                    uses configuration-and-switch-control;
                    description    
                "A switch controller external to the LayerProtocol.
                        The controller will coordinate one or more switches in one or more FCs related to the LayerProtocol";
                }
                leaf is-protection-lock-out {
                    type boolean;
                    default "false";
                    description    
                    "The resource is configured to temporarily not be available for use in the protection scheme(s) it is part of.
                        This overrides all other protection control states including forced.
                        If the item is locked out, then it cannot be used under any circumstances.
                        Note: Only relevant when part of a protection scheme.";
                }
                leaf fc-blocks-signal-to-lp {
                    type block-direction;
                    default "BLOCK_DIRECTION_NO_BLOCK";
                    description    
                    "Indicates whether the associated FC is blocking signal to/from the LTP.";
                }
                list lp-spec-reference-class-ref {
                    if-feature spectargetclass:-layerprotocol;
                    uses metaclass-class;
                    description    
                "Reference to the specific LpSpec class that defines the properties that augment the instance of LP.";
                }
                uses local-class;
                description    
                "The projection of an LTP into each transport layer is represented by a LayerProtocol (LP) instance. A LayerProtocol instance can be used for controlling termination and monitoring functionality. 
                    It can also be used for controlling the adaptation (i.e. aggregation, encapsulation and/or multiplexing of client signal), tandem connection monitoring, traffic conditioning and/or shaping functionality at an intermediate point along a connection. 
                    Where the client – server relationship is fixed 1:1 and immutable, the layers can be encapsulated in a single LTP instance. Where there is a n:1 relationship between client and server, the layers must be split over two separate instances of LTP. ";
            }
            grouping logical-termination-point {
                leaf-list server-ltp {
                    type leafref {
                        pathmust "/core-model:network-control-domain/core-model:network-element/core-model:ltp/core-model:";
                    require-instance false;
                    }
                must  'deref(.) = current()';
                    description     
                 "References contained LTPs representing servers of this LTP in an inverse multiplexing configuration (e.g. VCAT).";
                }
                leaf-list client-ltp {
                    type leafref {
                        pathmust "/core-model:network-control-domain/core-model:network-element/core-model:ltp/core-model:";
                    require-instance false;
                    }
                must  'deref(.) = current()';
                    description     
                 "References contained LTPs representing client traffic of this LTP for normal cases of multiplexing.";
                }
                list lp {
                    min-elements 1;
                    uses layer-protocol;
                    description    
                "Ordered list of LayerProtocols that this LTP is comprised of where the first entry in the list is the lowest server layer (e.g. physical).";
                }
                leaf connected-ltp {
                    type leafref {
                        pathmust "/core-model:network-control-domain/core-model:network-element/core-model:ltp/core-model:";
                    require-instance false;
                    }
                must  'deref(.) = current()';
                    description    
                    "Applicable in a simple context where two LTPs are associated via a non-adjustable enabled forwarding.
                        Reduces clutter removing the need for two additional LTPs and an FC with a pair of FcPorts.";
                }
                leaf peer-ltp {
                    type leafref {
                        pathmust "/core-model:network-control-domain/core-model:network-element/core-model:ltp/core-model:";
                    require-instance false;
                    }
                must  'deref(.) = current()';
                    description    
                    "References contained LTPs representing the reversal of orientation of flow where two LTPs are associated via a non-adjustable enabled forwarding and where the referenced LTP is fully dependent on this LTP.";
                }
                leaf-list physical-port-reference {
                    type string;
                    description     
                 "One or more text labels for the unmodeled physical port associated with the LTP.
                        In many cases there is no associated physical port.";
                }
                leaf-list ltp-in-other-view {
                    type leafref {
                        pathmust "/core-model:network-control-domain/core-model:network-element/core-model:ltp/core-model:";
                    require-instance false;
                    }
                must  'deref(.) = current()';
                    description     
                 "References one or more LTPs in other views that represent this LTP. 
                        The referencing LTP is the provider of capability.";
                }
                leaf ltp-direction {
                    type termination-direction;
                    description    
                    "The overall directionality of the LTP. 
                        - A BIDIRECTIONAL LTP must have at least some LPs that are BIDIRECTIONAL but may also have some SINK and/or SOURCE LPs.
                        - A SINK LTP can only contain SINK LPs
                        - A SOURCE LTP can only contain SOURCE LPs";
                }
                container access-port {
                    uses access-port;
                    description    
                "Provides a reference to the place where the signal is accessed. 
                        It may represent a physical place (some part of one or more connectors) or a virtual equivalent where there is no further protocol layering (visible).";
                }
                container transfer-capacity-pac {
                    uses transfer-capacity-pac;
                    description    
                "The LTP has as an inherent capacity derived from underlying capability.
                        The capacity of a particular LTP may be dependent upon other uses of resource in the device and hence it may vary over time.
                        The capacity of a Link is dependent upon the capacity of the LTPs at its ends.
                        An LTP may be an abstraction and virtualization of a subset of the underlying capability offered in a view or may be directly reflecting the underlying realization.";
                }
                list ltp-spec-reference-class-ref {
                    if-feature spectargetclass:-logicalterminationpoint;
                    min-elements 1;
                    uses metaclass-class;
                    description    
                "Provides a reference to a specification which is in the form of a class definition.
                        An instance of LTP will reference a class (by a universally unique id) that provides definition that extends the LTP including attributes and structure that are present in the LTP instance but that are not defined in the native LTP class.
";
                }
                leaf-list fd-rule-group {
                    type leafref {
                        pathmust "/core-model:network-control-domain/core-model:network-element/core-model:fd/core-model:";
                    require-instance false;
                    }
                must  'deref(.) = current()';
                    description     
                 "An LTP can reference FD rules that the FD that aggregates it also references so that the rules can then apply to the LTP.";
                }
                list embedded-clock {
                    uses clock;
                    description    
                "none";
                }
                container supporting-pc {
                    uses processing-construct;
                    description    
                "The functionality supporting this entity.";
                }
                uses global-class;
                description    
                "The LogicalTerminationPoint (LTP) class encapsulates the termination and adaptation functions of one or more transport layers represented by instances of LayerProtocol.
                    The encapsulated transport layers have a simple fixed 1:1 client-server relationship defined by association end ordering.
                    The structure of LTP supports all transport protocols including analogue, circuit and packet forms.";
            }
            grouping link-port {
                list ltp {
                    uses logical-termination-point;
                    description    
                "The LinkPort may be associated with more than one LTP when the LinkPort is bidirectional and the LTPs are unidirectional.
                        Multiple LTP
                        - Bidirectional LinkPort to two Uni-directional LTPs
                        Zero LTP
                        - BreakBeforeMake transition
                        - Planned LTP not yet in place
                        - Off-network LTP referenced through other mechanism.";
                }
                leaf role {
                    type port-role;
                    description    
                    "Each LinkPort of the Link has a role (e.g., symmetric, hub, spoke, leaf, root) in the context of the Link with respect to the Link capability. ";
                }
                leaf off-network-address {
                    type string;
                    description    
                    "A freeform opportunity to express a reference for a Port of the Link that is not visible and hence is outside the scope of the control domain (off-network).
                        This attribute is expected to convey a foreign identifier/name/address or a shared reference for some mid-span point at the boundary between two administrative domains.
                        This is a reference shared between the parties either side of the network boundary. 
                        The assumption is that the provider knows the mapping between network port and offNetworkAddress and the client knows the mapping between the client port and the offNetworkAddress and that the offNetworkAddress references some common point or pool of points. 
                        It may represent some physical location where the hand-off takes place. This attribute is used when an LTP cannot be referenced.
                        A Link with an Off-network end cannot be encompassed by an FD.";
                }
                leaf link-port-direction {
                    type port-direction;
                    description    
                    "The orientation of the defined flow at the LinkPort.";
                }
                leaf-list fc-port {
                    type leafref {
                        pathmust "/core-model:network-control-domain/core-model:network-element/core-model:ltp/core-model:embedded-clock/core-model:encapsulated-fc/core-model:fc-port/core-model:";
                    require-instance false;
                    }
                must  'deref(.) = current()';
                    description     
                 "Where a Link supports FCs each LinkPort of that Link supports the corresponding FcPorts.";
                }
                uses local-class;
                description    
                "The association of the Link to LTPs is made via LinkPort.
                    The LinkPort class models the access to the Link function. 
                    The traffic forwarding between the associated LinkPorts of the Link depends upon the type of Link.  
                    In cases where there is resilience, the LinkPort may convey the resilience role of the access to the Link. 
                    The Link can be considered as a component and the LinkPort as a Port on that component.";
            }
            grouping fd-port {
                leaf-list ltp {
                    type leafref {
                        pathmust "/core-model:network-control-domain/core-model:network-element/core-model:ltp/core-model:";
                    require-instance false;
                    }
                must  'deref(.) = current()';
                    max-elements 2;
                    description     
                 "An instance of FD is associated with zero or more LTP objects. 
                        The LTPs that bound the FD provide capacity for forwarding.
                        For asymmetric FDs, the association to the LTP is via the FdPort.";
                }
                leaf role {
                    type port-role;
                    description    
                    "Each FdPort of the FD has a role (e.g., symmetric, hub, spoke, leaf, root) in the context of the FD with respect to the FD capability. ";
                }
                leaf fd-port-direction {
                    type port-direction;
                    description    
                    "The orientation of the defined flow at the FdPort.";
                }
                leaf-list fc-port {
                    type leafref {
                        pathmust "/core-model:network-control-domain/core-model:network-element/core-model:ltp/core-model:embedded-clock/core-model:encapsulated-fc/core-model:fc-port/core-model:";
                    require-instance false;
                    }
                must  'deref(.) = current()';
                    description     
                 "Where an FD is asymmetric and hence has FdPorts and where that FD and supports FCs, appropriate FdPorts of that FD support the corresponding FcPorts.";
                }
                container pin {
                    uses pin;
                    description    
                "For media, a pin on the boundary of the FD.";
                }
                leaf-list fd-port {
                    type leafref {
                        pathmust "/core-model:network-control-domain/core-model:network-element/core-model:fd/core-model:fd-port/core-model:";
                    require-instance false;
                    }
                must  'deref(.) = current()';
                    max-elements 2;
                    description     
                 "An FdPort may have a direct association to another FdPort where there is a transition from one domain to another but where there has been no termination.";
                }
                uses local-class;
                description    
                "The association of the FD to LTPs may be direct for symmetric FDs and may be via FdPort for asymmetric FDs.
                    The FdPort class models the role of the access to the FD function. 
                    The capability to set up FCs between the associated FdPorts of the FD depends upon the type of FD. It is asymmetry in this capability that brings the need for FdPort.  
                    The FD can be considered as a component and the FdPort as a Port on that component.";
            }
            feature in-protection-context-if-server-of-protection-where-entire-server-is-to-be-excluded-from-use-for-protection {
            description    
                none;
            }
            feature spectargetclass-forwardingconstruct {
            description    
                none;
            }
            feature spectargetclass-link {
            description    
                none;
            }
            feature in-protection-context-where-the-fcport-is-to-be-excluded-from-use-for-protection {
            description    
                none;
            }
            feature spectargetclass:-layerprotocol {
            description    
                none;
            }
            feature spectargetclass:-logicalterminationpoint {
            description    
                none;
            }

        /****************************************
        * package diagrams
        **************************************/ 

        /****************************************
        * package associations
        **************************************/ 


    /****************************************
    * package core-foundation-model
    **************************************/ 
/****************************************
* typedef statements
**************************************/ 
            typedef date-and-time {
                type string;
                description    
                "This primitive type defines the date and time according to the following structure:
                    'yyyyMMddhhmmss.s[Z|{+|-}HHMm]' where:
                    yyyy    '0000'..'9999'    year
                    MM        '01'..'12'            month
                    dd        '01'..'31'            day
                    hh        '00'..'23'            hour
                    mm        '00'..'59'            minute
                    ss        '00'..'59'            second
                    s        '.0'..'.9'            tenth of second (set to '.0' if EMS or NE cannot support this granularity)
                    Z        'Z'                    indicates UTC (rather than local time)
                    {+|-}    '+' or '-'            delta from UTC
                    HH        '00'..'23'            time zone difference in hours
                    Mm        '00'..'59'            time zone difference in minutes.";
            }
            typedef bit-string {
                type string;
                description    
                "This primitive type defines a bit oriented string.
                    The size of the BitString will be defined in the valueRange property of the attribute; according to ASN.1 (X.680).
                    The semantic of each bit position will be defined in the Documentation field of the attribute.";
            }
            typedef printable-string {
                type string;
                description    
                "A string that only includes printable characters.";
            }
            typedef to-be-defined {
                type string;
                description    
                "This type is used when the actual type of the attribute is expected to be complex but where the type has not yet been developed. 
                    This type should only be used for attributes that are experimental.";
            }

/*********************************************
* grouping statements for complex data types
*******************************************/ 
            identity PORT_DIRECTION {
                description    
                "none";
            }
            identity PORT_DIRECTION_BIDIRECTIONAL {
                base PORT_DIRECTION;
                description    
                "The Port has both an INPUT flow and an OUTPUT flow defined.";
            }
            identity PORT_DIRECTION_INPUT {
                base PORT_DIRECTION;
                description    
                "The Port only has definition for a flow into the Forwarding entity (i.e. an ingress flow).";
            }
            identity PORT_DIRECTION_OUTPUT {
                base PORT_DIRECTION;
                description    
                "The Port only has definition for a flow out of the Forwarding entity (i.e. an egress flow).";
            }
            identity PORT_DIRECTION_UNIDENTIFIED_OR_UNKNOWN {
                base PORT_DIRECTION;
                description    
                "Not a normal state. The system is unable to determine the correct value.";
            }
            identity PORT_DIRECTION_OMNIDIRECTIONAL {
                base PORT_DIRECTION;
                description    
                "none";
            }
            identity FORWARDING_DIRECTION {
                description    
                "none";
            }
            identity FORWARDING_DIRECTION_BIDIRECTIONAL {
                base FORWARDING_DIRECTION;
                description    
                "The Forwarding entity supports both BIDIRECTIONAL flows at all Ports (i.e. all Ports have both an INPUT flow and an OUTPUT flow defined).";
            }
            identity FORWARDING_DIRECTION_UNIDIRECTIONAL {
                base FORWARDING_DIRECTION;
                description    
                "The Forwarding entity has Ports that are either INPUT or OUTPUT. It has no BIDIRECTIONAL Ports.";
            }
            identity FORWARDING_DIRECTION_UNDEFINED_OR_UNKNOWN {
                base FORWARDING_DIRECTION;
                description    
                "Not a normal state. The system is unable to determine the correct value.";
            }
            identity FORWARDING_DIRECTION_OMNIDIRECTIONAL {
                base FORWARDING_DIRECTION;
                description    
                "none";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base TERMINATION_DIRECTION;
                description    
                "Not a normal state. The system is unable to determine the correct value.";
            }
            identity EXTENDED_TERMINATION_DIRECTION {
                description    
                "none";
            }
            identity EXTENDED_TERMINATION_DIRECTION_CONTRA_DIRECTION_SINK {
                base EXTENDED_TERMINATION_DIRECTION;
                description    
                "The essential flow of the Termination entity is SINK (i.e. up the layer stack) but the INPUT flow of the Termination entity was provided by a SOURCE OUTPUT or taken from a SOURCE INPUT (duplicating the input signal) hence reversing the flow orientation from down the layer stack to up the layer stack.";
            }
            identity EXTENDED_TERMINATION_DIRECTION_CONTRA_DIRECTION_SOURCE {
                base EXTENDED_TERMINATION_DIRECTION;
                description    
                "The essential flow of the Termination entity is SOURCE (i.e. down the layer stack) but the OUTPUT flow of the Termination entity was fed to (and replaces) a SINK OUTPUT or was fed to a SINK INPUT (replacing the normal flow) hence reversing the flow orientation from down the layer stack to up the layer stack.";
            }
            identity TERMINATION_STATE {
                description    
                "none";
            }
            identity TERMINATION_STATE_LP_CAN_NEVER_TERMINATE {
                base TERMINATION_STATE;
                description    
                "A non-flexible case that can never be terminated.";
            }
            identity TERMINATION_STATE_LP_NOT_TERMINATED {
                base TERMINATION_STATE;
                description    
                "A flexible termination that can terminate but is currently not terminated.";
            }
            identity TERMINATION_STATE_TERMINATED_SERVER_TO_CLIENT_FLOW {
                base TERMINATION_STATE;
                description    
                "A flexible termination that is currently terminated for server to client flow only.";
            }
            identity TERMINATION_STATE_TERMINATED_CLIENT_TO_SERVER_FLOW {
                base TERMINATION_STATE;
                description    
                "A flexible termination that is currently terminated for client to server flow only.";
            }
            identity TERMINATION_STATE_TERMINATED_BIDIRECTIONAL {
                base TERMINATION_STATE;
                description    
                "A flexible termination that is currently terminated in both directions of flow.";
            }
            identity TERMINATION_STATE_LP_PERMENANTLY_TERMINATED {
                base TERMINATION_STATE;
                description    
                "A non-flexible termination that is always terminated (in both directions of flow for a bidirectional case and in the one direction of flow for both unidirectional cases).";
            }
            identity TERMINATION_STATE_TERMINATION_STATE_UNKNOWN {
                base TERMINATION_STATE;
                description    
                "There TerminationState cannot be determined.";
            }
            identity PROTECTION_REASON {
                description    
                "none";
            }
            identity PROTECTION_REASON_WAIT_TO_REVERT {
                base PROTECTION_REASON;
                description    
                "The resource is selected as control is waiting to restore to a preferred resource.";
            }
            identity PROTECTION_REASON_SIGNAL_DEGRADE {
                base PROTECTION_REASON;
                description    
                "The resource is selected as the best preferred resource is in signal degrade.";
            }
            identity PROTECTION_REASON_SIGNAL_FAIL {
                base PROTECTION_REASON;
                description    
                "The resource is selected as the best preferred resource is in signal fail.";
            }
            identity ROUTE_SELECTION_CONTROL {
                description    
                "none";
            }
            identity ROUTE_SELECTION_CONTROL_LOCK_OUT {
                base ROUTE_SELECTION_CONTROL;
                description    
                "The resource is configured to temporarily not be available for use in the protection scheme(s) it is part of.
                    This overrides all other protection control states including forced.
                    If the item is locked out, then it cannot be used under any circumstances.
                    Note: Only relevant when part of a protection scheme.
                    Note: if a protection process that has a relationship to the item (i.e. is one of the options the protection process may choose) is deactivated by being isFrozen = true) then the lockout request will be rejected. ";
            }
            identity ROUTE_SELECTION_REASON {
                description    
                "none";
            }
            identity SWITCH_CONTROL {
                description    
                "none";
            }
            identity SWITCH_CONTROL_NORMAL {
                base SWITCH_CONTROL;
                description    
                "No administrative control applied to the switch.";
            }
            identity SWITCH_CONTROL_MANUAL {
                base SWITCH_CONTROL;
                description    
                "Resource temporarily chosen by control configuration where the resource is not the preferred resource.
                    Preferred resource has highest priority.
                    Temporarily overrides reversion.
                    If this resource fails, it will switch to best available resource. 
                    If resource selected is shared and another FC requires the resource, then the selection control will change to Normal and switch to best available based upon normal rules.
                    Cannot manually switch a Forced switch, cannot remove a forced switch, cannot switch to a locked out item and will be rejected if the protection process is deactivated by being Freeze = true).
                    A manual switch/route that is selecting an FcPort, LTP, FC, Link or Route that is subsequently set to LOCK_OUT will have the manual removed (changed to NORMAL) and will switch away from the FcPort with LOCK_OUT to best available based upon normal rules.
                    A manual switch that is selecting an FcPort that is subsequently selected by a Forced switch will be restored to normal operation and the manual will be removed.
                    A manual switch/route that is selecting an FcPort, LTP, FC, Link or Route that is subsequently manual selected by another switch/route will have the manual removed and will switch away from the FcPort.
                    Can be returned to NORMAL by configuration action.";
            }
            identity SWITCH_CONTROL_FORCED {
                base SWITCH_CONTROL;
                description    
                "Resource temporarily chosen by control configuration where the resource is not the preferred resource.
                    Preferred resource has highest priority.
                    Temporarily overrides reversion.
                    If this resource fails it will NOT switch. 
                    If resource selected is shared and another FC requires the resource through a FORCE on that FC and the FC is of a higher FcPriority then the selection control on this FC will change to NORMAL and switch to best available based upon normal rules.
                    If the resource selected is then set to LOCK_OUT then the selection control will change to NORMAL and switch to best available based upon normal rules.
                    Can be returned to NORMAL by configuration action.";
            }
            identity SWITCH_STATE_REASON {
                description    
                "none";
            }
            identity REVERSION_MODE {
                description    
                "none";
            }
            identity REVERSION_MODE_REVERTIVE {
                base REVERSION_MODE;
                description    
                "An FC switched to a lower priority (non-preferred) resource will revert to a higher priority (preferred) resource when that recovers (potentially after some hold-off time).";
            }
            identity REVERSION_MODE_NON-REVERTIVE {
                base REVERSION_MODE;
                description    
                "An FC switched to a lower priority (non-preferred) resource will not revert to a higher priority (preferred) resource when that recovers.";
            }
            identity RESILIENCE_CONTROL {
                description    
                "none";
            }
            identity RESILIENCE_CONTROL_QUIESCENT {
                base RESILIENCE_CONTROL;
                description    
                "none";
            }
            identity RESILIENCE_CONTROL_RESTORING {
                base RESILIENCE_CONTROL;
                description    
                "none";
            }
            identity RESILIENCE_CONTROL_RECOVERY_FAILED {
                base RESILIENCE_CONTROL;
                description    
                "none";
            }
            identity RESILIENCE_CONTROL_UNKNOWN {
                base RESILIENCE_CONTROL;
                description    
                "none";
            }
            identity RUN_MODE {
                description    
                "none";
            }
            identity RUN_MODE_FREE_RUN {
                base RUN_MODE;
                description    
                "The clock is not synchronized to another clock.";
            }
            identity RUN_MODE_LOCKED {
                base RUN_MODE;
                description    
                "The clock is synchronized to another clock.";
            }
            identity RUN_MODE_HOLD_OVER {
                base RUN_MODE;
                description    
                "The clock was previously synchronized to another clock but that timing input has been lost.
                    The clock is set to the last known synchronization.";
            }
            identity LAYER_PROTOCOL_NAME {
                description    
                "none";
            }
            identity LAYER_PROTOCOL_NAME_PHOTONIC_MEDIA {
                base LAYER_PROTOCOL_NAME;
                description    
                "The characteristic information is that of a channel able to carry photons and of the photon source/sink.";
            }
            identity LAYER_PROTOCOL_NAME_OTU_AND_ODU {
                base LAYER_PROTOCOL_NAME;
                description    
                "The characteristic information is that of a channel able to carry ODU/OTU protocol (OTN) and of the ODU/OTU source/sink.";
            }
            identity LAYER_PROTOCOL_NAME_ETHERNET {
                base LAYER_PROTOCOL_NAME;
                description    
                "The characteristic information is that of a channel able to carry Ethernet protocol and of the Ethernet protocol source/sink.";
            }
            identity OPERATIONAL_STATE {
                description    
                "none";
            }
            identity OPERATIONAL_STATE_DISABLED {
                base OPERATIONAL_STATE;
                description    
                "The resource is unable to meet the SLA of the user of the resource. 
                    If no (explicit) SLA is defined the resource is disabled if it is totally inoperable and unable to provide service to the user.";
            }
            identity OPERATIONAL_STATE_ENABLED {
                base OPERATIONAL_STATE;
                description    
                "The resource is partially or fully operable and available for use.";
            }
            identity ADMINISTRATIVE_STATE {
                description    
                "none";
            }
            identity ADMINISTRATIVE_STATE_LOCKED {
                base ADMINISTRATIVE_STATE;
                description    
                "Users are administratively prohibited from making use of the resource.";
            }
            identity ADMINISTRATIVE_STATE_UNLOCKED {
                base ADMINISTRATIVE_STATE;
                description    
                "Users are allowed to use the resource.";
            }
            identity ADMINISTRATIVE_STATE_SHUTTING_DOWN {
                base ADMINISTRATIVE_STATE;
                description    
                "The entity is administratively restricted to existing instances of use only. There may be specific actions to remove existing uses. No new instances of use can be enabled.
                    The resource automatically transitions to “locked” when the last user quits. 
                    The administrative state is not visible in the client context. 
                    The lifecycle state “pending removal” should be used to indicate to the client that the provider intends to remove the resource.";
            }
            identity ADMINISTRATIVE_CONTROL {
                description    
                "none";
            }
            identity ADMINISTRATIVE_CONTROL_UNLOCK {
                base ADMINISTRATIVE_CONTROL;
                description    
                "The intention is for the entity to become unlocked.
                    The entity may already be UNLOCKED.";
            }
            identity ADMINISTRATIVE_CONTROL_LOCK_PASSIVE {
                base ADMINISTRATIVE_CONTROL;
                description    
                "The intention is for the entity to become locked but no effort is expected to move to the Locked state (the state will be achieved once all users stop using the resource). 
                    The entity may be LOCKED.";
            }
            identity ADMINISTRATIVE_CONTROL_LOCK_ACTIVE {
                base ADMINISTRATIVE_CONTROL;
                description    
                "The intention is for the entity to become locked and it is expected that effort will be made to move to the Locked state (users will be actively removed). 
                    The entity may already be LOCKED.";
            }
            identity ADMINISTRATIVE_CONTROL_LOCK_IMMEDIATE {
                base ADMINISTRATIVE_CONTROL;
                description    
                "The intention is for the entity to become locked and it is expected to move to the Locked state immediately (users will be force removed). 
                    The entity may already be LOCKED.";
            }
            identity ADMINISTRATIVE_CONTROL_QUIESCENT {
                base ADMINISTRATIVE_CONTROL;
                description    
                "The administrative state is at a stable value (LOCKED/UNLOCKED) and no action is being taken.";
            }
            identity LIFECYCLE_STATE {
                description    
                "none";
            }
            identity LIFECYCLE_STATE_PLANNED {
                base LIFECYCLE_STATE;
                description    
                "The resource is planned but is not present in the network.
                    Should include a 'time' when the resources are expected to be installed.";
            }
            identity LIFECYCLE_STATE_POTENTIAL_AVAILABLE {
                base LIFECYCLE_STATE;
                description    
                "The supporting resources are present in the network but are shared with other clients; or require further configuration before they can be used; or both.
                    (1) When a potential resource is configured and allocated to a client it is moved to the INSTALLED state for that client.
                    (2) If the potential resource has been consumed (e.g. allocated to another client) it is moved to the POTENTIAL BUSY state for all other clients.";
            }
            identity LIFECYCLE_STATE_POTENTIAL_BUSY {
                base LIFECYCLE_STATE;
                description    
                "The supporting resources are present in the network but have been allocated to other clients.";
            }
            identity LIFECYCLE_STATE_INSTALLED {
                base LIFECYCLE_STATE;
                description    
                "The resource is present in the network and is capable of providing the service.";
            }
            identity LIFECYCLE_STATE_PENDING_REMOVAL {
                base LIFECYCLE_STATE;
                description    
                "The resource has been marked for removal. Should include a “time” when the resources are expected to be removed.";
            }
            identity BLOCK_DIRECTION {
                description    
                "none";
            }
            identity BLOCK_DIRECTION_NO_BLOCK {
                base BLOCK_DIRECTION;
                description    
                "The FC is not blocking signal related to the LTP.";
            }
            identity BLOCK_DIRECTION_INGRESS_BLOCK {
                base BLOCK_DIRECTION;
                description    
                "The FC is blocking signal that is flowing into the LTP from the FC.";
            }
            identity BLOCK_DIRECTION_EGRESS_BLOCK {
                base BLOCK_DIRECTION;
                description    
                "The FC is blocking signal flowing out of the LTP to the FC.";
            }
            identity BLOCK_DIRECTION_BIDIRECTIONAL_BLOCK {
                base BLOCK_DIRECTION;
                description    
                "The FC is blocking both directions of traffic, i.e. Ingress and Egress, to/from the LTP.";
            }
            identity CONNECTOR_AND_PIN_ORIENTATION {
                description    
                "none";
            }
            identity CONNECTOR_AND_PIN_ORIENTATION_MALE {
                base CONNECTOR_AND_PIN_ORIENTATION;
                description    
                "The connecting elements are dominantly protrusions.";
            }
            identity CONNECTOR_AND_PIN_ORIENTATION_FEMALE {
                base CONNECTOR_AND_PIN_ORIENTATION;
                description    
                "The connecting elements are dominantly indentations.";
            }
            identity CONNECTOR_AND_PIN_ORIENTATION_SYMMETRIC_NEUTRAL {
                base CONNECTOR_AND_PIN_ORIENTATION;
                description    
                "The pin (and housing) orientation combination is such that it is symmetric so a connector is compatible with itself.
                    The connecting element may be a surface rather than protrusions or indentations.";
            }
            identity EQUIPMENT_CATEGORY {
                description    
                "none";
            }
            identity EQUIPMENT_CATEGORY_SUBRACK {
                base EQUIPMENT_CATEGORY;
                description    
                "An assembly with holders designed to accommodate CIRCUIT_PACKs. 
                    The assembly is designed to be mounted in a RACK.";
            }
            identity EQUIPMENT_CATEGORY_CIRCUIT_PACK {
                base EQUIPMENT_CATEGORY;
                description    
                "An assembly with connectors compatible with those in a holder.
                    The assembly is designed to be mounted in a holder (SLOT) of a SUBRACK.
                    May also support holders (SLOTs) for SMALL_FORMFACTOR_PLUGGABLEs.";
            }
            identity EQUIPMENT_CATEGORY_SMALL_FORMFACTOR_PLUGGABLE {
                base EQUIPMENT_CATEGORY;
                description    
                "A small assembly (compared to a CIRCUIT_PACK) with connectors compatible with those in a holder.
                    The assembly is designed to be mounted in a holder (SLOT) of a CIRCUIT_PACK or STAND_ALONE_UNIT.";
            }
            identity EQUIPMENT_CATEGORY_STAND_ALONE_UNIT {
                base EQUIPMENT_CATEGORY;
                description    
                "An assembly with connectors for cabling and potentially with holders.
                    The assembly is designed to be mounted in a freeform environment (on a table or simple mechanical cabinet).
                    May support holders (SLOTs) for CIRCUIT_PACKs or for SMALL_FORMFACTOR_PLUGGABLEs.";
            }
            identity EQUIPMENT_CATEGORY_RACK {
                base EQUIPMENT_CATEGORY;
                description    
                "A mechanical assembly with cabling and predefined mounting points for particular SUBRACK types.
                    The assembly is designed to be mounted on the floor in a row with other RACKs.";
            }
            identity HOLDER_CATEGORY {
                description    
                "none";
            }
            identity HOLDER_CATEGORY_SLOT {
                base HOLDER_CATEGORY;
                description    
                "A guided holder with fixed connectors.
                    The guided holder is designed to take a particular form of CIRCUIT_PACK or SMALL_FORMFACTOR_PLUGGABLE";
            }
            identity FORWARDING_RULE {
                description    
                "none";
            }
            identity FORWARDING_RULE_CANNOT_FORWARD_ACROSS_FD_LINK {
                base FORWARDING_RULE;
                description    
                "LTPs referenced by the FD (or indirectly by the Link between FDs) cannot have FCs created between them.
                    This rule overrides all others.";
            }
            identity FORWARDING_RULE_MUST_FORWARD_ACROSS_FD_LINK {
                base FORWARDING_RULE;
                description    
                "LTPs referenced by the FD (or indirectly by the Link between FDs) MUST have FCs created between them.
                    This rule overrides all others except the CANNOT_FORWARD rule.";
            }
            identity FORWARDING_RULE_MAY_FORWARD_ACROSS_FD_LINK {
                base FORWARDING_RULE;
                description    
                "LTPs referenced by the FD (or indirectly by the Link between FDs) may have FCs created between them.
                    FCs may not be created between points that are not related by this rule either directly in an FD or indirectly via a Link linking two or more FDs.
                    For a Link points in an FD at one end of the Link can be connected to points in an FD at an other end of the Link.";
            }
            identity FORWARDING_RULE_NULL_FORWARDING_RULE {
                base FORWARDING_RULE;
                description    
                "none";
            }
            identity RULE_TYPE {
                description    
                "none";
            }
            identity RULE_TYPE_FORWARDING {
                base RULE_TYPE;
                description    
                "The rule relates to creation of FCs.";
            }
            identity RULE_TYPE_COST {
                base RULE_TYPE;
                description    
                "The rule relates to forwarding cost.";
            }
            identity RULE_TYPE_RISK {
                base RULE_TYPE;
                description    
                "The rule relates to forwarding risk.";
            }
            identity RULE_TYPE_CAPACITY {
                base RULE_TYPE;
                description    
                "none";
            }
            identity PORT_ROLE_RULE_OPTION {
                description    
                "none";
            }
            identity PORT_ROLE_RULE_OPTION_SAME_ROLE {
                base PORT_ROLE_RULE_OPTION;
                description    
                "The ports to which the rule applies must have role from the list in PortRole.";
            }
            identity PORT_ROLE_RULE_OPTION_DIFFERENT_ROLE {
                base PORT_ROLE_RULE_OPTION;
                description    
                "The ports to which the rule applies must not have a role from the list in PortRole.";
            }
            identity PORT_ROLE_RULE_OPTION_ANY_ROLE {
                base PORT_ROLE_RULE_OPTION;
                description    
                "The rule applies to any role of port.";
            }
            identity SIGNAL_PROPERTY_VALUE_RULE {
                description    
                "none";
            }
            identity SIGNAL_PROPERTY_VALUE_RULE_SAME_VALUE {
                base SIGNAL_PROPERTY_VALUE_RULE;
                description    
                "none";
            }
            identity SIGNAL_PROPERTY_VALUE_RULE_ANY_VALUE {
                base SIGNAL_PROPERTY_VALUE_RULE;
                description    
                "none";
            }
            identity PARTNER {
                description    
                "none";
            }
            identity PARTNER_FC {
                base PARTNER;
                description    
                "ForwardingConstruct.";
            }
            identity PARTNER_FD {
                base PARTNER;
                description    
                "ForwardingDomain.";
            }
            identity PARTNER_LINK {
                base PARTNER;
                description    
                "Link.";
            }
            identity PARTNER_CASC {
                base PARTNER;
                description    
                "ConfigurationAndSwitchController.";
            }
            identity PARTNER_CC {
                base PARTNER;
                description    
                "ControlConstruct.";
            }
            identity PARTNER_CD {
                base PARTNER;
                description    
                "ConstraintDomain.";
            }
            identity PARTNER_PC {
                base PARTNER;
                description    
                "ProcessingConstruct.";
            }
            identity PARTNER_PEER {
                base PARTNER;
                description    
                "LTP peer.";
            }
            identity PARTNER_CLIENT {
                base PARTNER;
                description    
                "LTP client.";
            }
            identity PARTNER_SERVER {
                base PARTNER;
                description    
                "LTP server.";
            }
            identity PARTNER_VIEW {
                base PARTNER;
                description    
                "LTP in other view.";
            }
            identity TASK_LIFECYCLE_STATE {
                description    
                "none";
            }
            identity TASK_LIFECYCLE_STATE_RUNNING {
                base TASK_LIFECYCLE_STATE;
                description    
                "The task is running.";
            }
            identity TASK_LIFECYCLE_STATE_PAUSED {
                base TASK_LIFECYCLE_STATE;
                description    
                "The task has been paused.";
            }
            identity TASK_LIFECYCLE_STATE_WAITING {
                base TASK_LIFECYCLE_STATE;
                description    
                "The task is waiting for input etc.";
            }
            identity TASK_LIFECYCLE_STATE_ABORTING {
                base TASK_LIFECYCLE_STATE;
                description    
                "The task is aborting.";
            }
            identity TASK_LIFECYCLE_STATE_COMPLETED {
                base TASK_LIFECYCLE_STATE;
                description    
                "The task has been completed successfully.";
            }
            identity TASK_LIFECYCLE_STATE_ABORTED {
                base TASK_LIFECYCLE_STATE;
                description    
                "The task has been aborted.";
            }
            identity TASK_LIFECYCLE_STATE_ATTEMPTING_ROLLBACK {
                base TASK_LIFECYCLE_STATE;
                description    
                "The task is attempting to return the controlled system to a previous state.";
            }
            identity TASK_LIFECYCLE_STATE_ROLLBACK_COMPLETE {
                base TASK_LIFECYCLE_STATE;
                description    
                "The task has completed a roll back action.";
            }
            identity TASK_LIFECYCLE_STATE_ABANDONING {
                base TASK_LIFECYCLE_STATE;
                description    
                "Task is abandoning.";
            }
            identity TASK_LIFECYCLE_STATE_ABANDONED {
                base TASK_LIFECYCLE_STATE;
                description    
                "The task has been abandoned and is no longer running.";
            }
            identity TASK_LIFECYCLE_STATE_FAILED {
                base TASK_LIFECYCLE_STATE;
                description    
                "The task has failed.";
            }
            identity TASK_LIFECYCLE_STATE_ARCHIVED {
                base TASK_LIFECYCLE_STATE;
                description    
                "The task has been archived (and is no longer running).";
            }
            identity PROGRESS_STATUS {
                description    
                "none";
            }
            identity PROGRESS_STATUS_COMPLETE {
                base PROGRESS_STATUS;
                description    
                "none";
            }
            identity PROGRESS_STATUS_IN_PROGRESS {
                base PROGRESS_STATUS;
                description    
                "none";
            }
            identity PROGRESS_STATUS_FAILED {
                base PROGRESS_STATUS;
                description    
                "none";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity.";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity.";
            }
            identity TERMINATION_DIRECTION_UNDEFINED_OR_UNKNOWN {
                base TERMINATION_DIRECTION;
                description    
                "Not a normal state. The system is unable to determine the correct value.";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base TERMINATION_DIRECTION;
                description    
                "Not a normal state. The system is unable to determine the correct value.";
            }
            identity ACTION_VERBS {
                description    
                "none";
            }
            identity ACTION_VERBS_CREATE_POST_ADD {
                base ACTION_VERBS;
                description    
                "none";
            }
            identity ACTION_VERBS_SET_UPDATE_PUT_MODIFY_WRITE_ADD {
                base ACTION_VERBS;
                description    
                "none";
            }
            identity ACTION_VERBS_GET_READ {
                base ACTION_VERBS;
                description    
                "none";
            }
            identity ACTION_VERBS_DELETE_REMOVE {
                base ACTION_VERBS;
                description    
                "none";
            }
            identity DIRECTION {
                description    
                "none";
            }
            identity DIRECTION_IN {
                base DIRECTION;
                description    
                "none";
            }
            identity DIRECTION_OUT {
                base DIRECTION;
                description    
                "none";
            }
            identity DIRECTION_BIDIRECTIONAL {
                base DIRECTION;
                description    
                "none";
            }
            identity ACTION_VERBS {
                description    
                "none";
            }
            identity ACTION_VERBS_CREATE_POST_ADD {
                base ACTION_VERBS;
                description    
                "Cause the addition of some structure.";
            }
            identity ACTION_VERBS_SET_UPDATE_PUT_MODIFY_WRITE_ADD {
                base ACTION_VERBS;
                description    
                "Cause the adjustment to some properties.";
            }
            identity ACTION_VERBS_GET_READ {
                base ACTION_VERBS;
                description    
                "Acquire information.";
            }
            identity ACTION_VERBS_DELETE_REMOVE {
                base ACTION_VERBS;
                description    
                "Eliminate some structure.";
            }
            identity ACTIVITY_DIRECTIVE {
                description    
                "none";
            }
            identity ACTIVITY_DIRECTIVE_STRUCTURE_IS_NOT {
                base ACTIVITY_DIRECTIVE;
                description    
                "The structure defined should not be present. No part should be present (within the stated degrees of precision.";
            }
            identity ACTIVITY_DIRECTIVE_NEW_STRUCTURE_AND_VALUES {
                base ACTIVITY_DIRECTIVE;
                description    
                "None of the structure stated is expected to be present, but is required.";
            }
            identity ACTIVITY_DIRECTIVE_INCREMENTAL_STRUCTURE_AND_VALUES {
                base ACTIVITY_DIRECTIVE;
                description    
                "The structure stated is an increment on what already exists.
                    Increment in this case may also be decrement.";
            }
            identity ACTIVITY_DIRECTIVE_ONLY_VALUES_IN_EXISTING_STRUCTURE {
                base ACTIVITY_DIRECTIVE;
                description    
                "Only values should be modified, no new structure should be created and no structure should be deleted.";
            }
            identity ACTIVITY_DIRECTIVE_DEFINED_BY_VERB {
                base ACTIVITY_DIRECTIVE;
                description    
                "A verb is provided to give guidance (such as Create).";
            }
            identity ACTION_EFFORT {
                description    
                "none";
            }
            identity ACTION_EFFORT_BEST_EFFORT {
                base ACTION_EFFORT;
                description    
                "none";
            }
            identity ACTION_EFFORT_EXACT_MATCH {
                base ACTION_EFFORT;
                description    
                "none";
            }
            identity PAUSE_RESUME_RULE {
                description    
                "none";
            }
            identity PAUSE_RESUME_RULE_NO_PAUSE_POSSIBLE {
                base PAUSE_RESUME_RULE;
                description    
                "none";
            }

        /****************************************
        * package super-classes-and-common-packages
        **************************************/ 
            /****************************************
            * grouping statements for object classes
            **************************************/ 
                grouping name {
                    list name {
                        min-elements 1;
                        uses name-and-value;
                        description    
                "List of names.";
                    }
                    description    
                "Name: A property of an entity with a value that is unique in some namespace but may change during the life of the entity. A name carries no semantics with respect to the purpose of the entity.";
                }
                grouping global-class {
                    list local-id {
                        uses name-and-value;
                        description    
                "An identifier that is unique in the context of some scope that is less than the global scope.
                            (This should be considered in the context of Identifier: A property of an entity/role with a value that is unique within an identifier space, where the identifier space is itself unique, and immutable. The identifier therefore represents the identity of the entity/role. An identifier carries no semantics with respect to the purpose of the entity.)";
                    }
                    leaf uuid {
                        type universal-id;
                        description    
                    "UUID: An identifier that is universally unique
                            (This should be considered in the context of Identifier: A property of an entity/role with a value that is unique within an identifier space, where the identifier space is itself globally unique, and immutable. An identifier carries no semantics with respect to the purpose or state of the entity)
                            The uuid should be treated as opaque by the user.";
                    }
                    uses name;
                    uses label;
                    uses extension;
                    uses state-pac;
                    uses address;
                    description    
                "Represents a type of thing (an Entity) that has instances which can exist in their own right (independently of any others).
                        Entity: Has identity, defined boundary, properties, functionality and lifecycle in a global context.
                        (This should be considered in the context of a Class: (usage) The representation of a thing that may be an entity or an inseparable Entity Feature).";
                }
                grouping local-class {
                    list local-id {
                        min-elements 1;
                        uses name-and-value;
                        description    
                "An identifier that is unique in the context of some scope that is less than the global scope.
                            (This should be considered in the context of Identifier: A property of an entity/role with a value that is unique within an identifier space, where the identifier space is itself unique, and immutable. The identifier therefore represents the identity of the entity/role. An identifier carries no semantics with respect to the purpose of the entity.)";
                    }
                    uses name;
                    uses label;
                    uses extension;
                    uses state-pac;
                    uses address;
                    description    
                "A LocalClass represents a Feature of an Entity. It is inseparable from a GlobalClass but is a distinct feature of that GlobalClass such that the instances of LocalClass are able to have associations to other instances.
                        Feature of an Entity: An inseparable, externally distinguishable part of an entity.
                        The mandatory LocalId of the LocalClass instance is unique in the context of the GlobalClass from which it is inseparable.
                        (This should be considered in the context of a Class: (usage) The representation of a thing that may be an entity or an inseparable feature of an entity.)
                        ";
                }
                grouping label {
                    list label {
                        uses name-and-value;
                        description    
                "List of labels.";
                    }
                    description    
                "A property of an entity with a value that is not expected to be unique and is allowed to change. A label carries no semantics with respect to the purpose of the entity and has no effect on the entity behavior or state.";
                }
                grouping extension {
                    list extension {
                        uses name-and-value;
                        description    
                "List of simple name-value extensions.";
                    }
                    description    
                "Extension provides an opportunity to define properties not declared in the class that extend the class enabling a realization with simple ad-hoc extension of standard classes to be conformant.";
                }
                grouping universal-id-authority {
                    leaf uuid {
                        type universal-id;
                        description    
                    "The UUID for the UUID authority.";
                    }
                    description    
                "Represents the authority that controls the allocation of UUIDs.";
                }
                grouping name-and-value-authority {
                    leaf uuid {
                        type universal-id;
                        description    
                    "The UUID for the NameAndValueAuthority.";
                    }
                    description    
                "Represents the authority that controls the legal values for the names and values of a name/value attribute.";
                }
                grouping conditional-package {
                    uses extension;
                    uses label;
                    description    
                "The base class for conditional packages.";
                }
                grouping address {
                    list address {
                        uses address;
                        description    
                "One or more descriptions of the location.";
                    }
                    description    
                "Provides an opportunity to state the location of the entity via one or more hierarchies of narrowing contexts.";
                }

/****************************************
* typedef statements
**************************************/ 
                typedef universal-id {
                    type string;
                    description    
                "The universal ID value where the mechanism for generation is defined by some authority not directly referenced in the structure.
                        An example structure is [IETF RFC4122].";
                }

/*********************************************
* grouping statements for complex data types
*******************************************/ 
                identity PORT_DIRECTION {
                    description    
                "none";
                }
                identity PORT_DIRECTION_BIDIRECTIONAL {
                    base PORT_DIRECTION;
                    description    
                "The Port has both an INPUT flow and an OUTPUT flow defined.";
                }
                identity PORT_DIRECTION_INPUT {
                    base PORT_DIRECTION;
                    description    
                "The Port only has definition for a flow into the Forwarding entity (i.e. an ingress flow).";
                }
                identity PORT_DIRECTION_OUTPUT {
                    base PORT_DIRECTION;
                    description    
                "The Port only has definition for a flow out of the Forwarding entity (i.e. an egress flow).";
                }
                identity PORT_DIRECTION_UNIDENTIFIED_OR_UNKNOWN {
                    base PORT_DIRECTION;
                    description    
                "Not a normal state. The system is unable to determine the correct value.";
                }
                identity PORT_DIRECTION_OMNIDIRECTIONAL {
                    base PORT_DIRECTION;
                    description    
                "none";
                }
                identity FORWARDING_DIRECTION {
                    description    
                "none";
                }
                identity FORWARDING_DIRECTION_BIDIRECTIONAL {
                    base FORWARDING_DIRECTION;
                    description    
                "The Forwarding entity supports both BIDIRECTIONAL flows at all Ports (i.e. all Ports have both an INPUT flow and an OUTPUT flow defined).";
                }
                identity FORWARDING_DIRECTION_UNIDIRECTIONAL {
                    base FORWARDING_DIRECTION;
                    description    
                "The Forwarding entity has Ports that are either INPUT or OUTPUT. It has no BIDIRECTIONAL Ports.";
                }
                identity FORWARDING_DIRECTION_UNDEFINED_OR_UNKNOWN {
                    base FORWARDING_DIRECTION;
                    description    
                "Not a normal state. The system is unable to determine the correct value.";
                }
                identity FORWARDING_DIRECTION_OMNIDIRECTIONAL {
                    base FORWARDING_DIRECTION;
                    description    
                "none";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base TERMINATION_DIRECTION;
                    description    
                "Not a normal state. The system is unable to determine the correct value.";
                }
                identity EXTENDED_TERMINATION_DIRECTION {
                    description    
                "none";
                }
                identity EXTENDED_TERMINATION_DIRECTION_CONTRA_DIRECTION_SINK {
                    base EXTENDED_TERMINATION_DIRECTION;
                    description    
                "The essential flow of the Termination entity is SINK (i.e. up the layer stack) but the INPUT flow of the Termination entity was provided by a SOURCE OUTPUT or taken from a SOURCE INPUT (duplicating the input signal) hence reversing the flow orientation from down the layer stack to up the layer stack.";
                }
                identity EXTENDED_TERMINATION_DIRECTION_CONTRA_DIRECTION_SOURCE {
                    base EXTENDED_TERMINATION_DIRECTION;
                    description    
                "The essential flow of the Termination entity is SOURCE (i.e. down the layer stack) but the OUTPUT flow of the Termination entity was fed to (and replaces) a SINK OUTPUT or was fed to a SINK INPUT (replacing the normal flow) hence reversing the flow orientation from down the layer stack to up the layer stack.";
                }
                identity TERMINATION_STATE {
                    description    
                "none";
                }
                identity TERMINATION_STATE_LP_CAN_NEVER_TERMINATE {
                    base TERMINATION_STATE;
                    description    
                "A non-flexible case that can never be terminated.";
                }
                identity TERMINATION_STATE_LP_NOT_TERMINATED {
                    base TERMINATION_STATE;
                    description    
                "A flexible termination that can terminate but is currently not terminated.";
                }
                identity TERMINATION_STATE_TERMINATED_SERVER_TO_CLIENT_FLOW {
                    base TERMINATION_STATE;
                    description    
                "A flexible termination that is currently terminated for server to client flow only.";
                }
                identity TERMINATION_STATE_TERMINATED_CLIENT_TO_SERVER_FLOW {
                    base TERMINATION_STATE;
                    description    
                "A flexible termination that is currently terminated for client to server flow only.";
                }
                identity TERMINATION_STATE_TERMINATED_BIDIRECTIONAL {
                    base TERMINATION_STATE;
                    description    
                "A flexible termination that is currently terminated in both directions of flow.";
                }
                identity TERMINATION_STATE_LP_PERMENANTLY_TERMINATED {
                    base TERMINATION_STATE;
                    description    
                "A non-flexible termination that is always terminated (in both directions of flow for a bidirectional case and in the one direction of flow for both unidirectional cases).";
                }
                identity TERMINATION_STATE_TERMINATION_STATE_UNKNOWN {
                    base TERMINATION_STATE;
                    description    
                "There TerminationState cannot be determined.";
                }
                identity PROTECTION_REASON {
                    description    
                "none";
                }
                identity PROTECTION_REASON_WAIT_TO_REVERT {
                    base PROTECTION_REASON;
                    description    
                "The resource is selected as control is waiting to restore to a preferred resource.";
                }
                identity PROTECTION_REASON_SIGNAL_DEGRADE {
                    base PROTECTION_REASON;
                    description    
                "The resource is selected as the best preferred resource is in signal degrade.";
                }
                identity PROTECTION_REASON_SIGNAL_FAIL {
                    base PROTECTION_REASON;
                    description    
                "The resource is selected as the best preferred resource is in signal fail.";
                }
                identity ROUTE_SELECTION_CONTROL {
                    description    
                "none";
                }
                identity ROUTE_SELECTION_CONTROL_LOCK_OUT {
                    base ROUTE_SELECTION_CONTROL;
                    description    
                "The resource is configured to temporarily not be available for use in the protection scheme(s) it is part of.
                        This overrides all other protection control states including forced.
                        If the item is locked out, then it cannot be used under any circumstances.
                        Note: Only relevant when part of a protection scheme.
                        Note: if a protection process that has a relationship to the item (i.e. is one of the options the protection process may choose) is deactivated by being isFrozen = true) then the lockout request will be rejected. ";
                }
                identity ROUTE_SELECTION_REASON {
                    description    
                "none";
                }
                identity SWITCH_CONTROL {
                    description    
                "none";
                }
                identity SWITCH_CONTROL_NORMAL {
                    base SWITCH_CONTROL;
                    description    
                "No administrative control applied to the switch.";
                }
                identity SWITCH_CONTROL_MANUAL {
                    base SWITCH_CONTROL;
                    description    
                "Resource temporarily chosen by control configuration where the resource is not the preferred resource.
                        Preferred resource has highest priority.
                        Temporarily overrides reversion.
                        If this resource fails, it will switch to best available resource. 
                        If resource selected is shared and another FC requires the resource, then the selection control will change to Normal and switch to best available based upon normal rules.
                        Cannot manually switch a Forced switch, cannot remove a forced switch, cannot switch to a locked out item and will be rejected if the protection process is deactivated by being Freeze = true).
                        A manual switch/route that is selecting an FcPort, LTP, FC, Link or Route that is subsequently set to LOCK_OUT will have the manual removed (changed to NORMAL) and will switch away from the FcPort with LOCK_OUT to best available based upon normal rules.
                        A manual switch that is selecting an FcPort that is subsequently selected by a Forced switch will be restored to normal operation and the manual will be removed.
                        A manual switch/route that is selecting an FcPort, LTP, FC, Link or Route that is subsequently manual selected by another switch/route will have the manual removed and will switch away from the FcPort.
                        Can be returned to NORMAL by configuration action.";
                }
                identity SWITCH_CONTROL_FORCED {
                    base SWITCH_CONTROL;
                    description    
                "Resource temporarily chosen by control configuration where the resource is not the preferred resource.
                        Preferred resource has highest priority.
                        Temporarily overrides reversion.
                        If this resource fails it will NOT switch. 
                        If resource selected is shared and another FC requires the resource through a FORCE on that FC and the FC is of a higher FcPriority then the selection control on this FC will change to NORMAL and switch to best available based upon normal rules.
                        If the resource selected is then set to LOCK_OUT then the selection control will change to NORMAL and switch to best available based upon normal rules.
                        Can be returned to NORMAL by configuration action.";
                }
                identity SWITCH_STATE_REASON {
                    description    
                "none";
                }
                identity REVERSION_MODE {
                    description    
                "none";
                }
                identity REVERSION_MODE_REVERTIVE {
                    base REVERSION_MODE;
                    description    
                "An FC switched to a lower priority (non-preferred) resource will revert to a higher priority (preferred) resource when that recovers (potentially after some hold-off time).";
                }
                identity REVERSION_MODE_NON-REVERTIVE {
                    base REVERSION_MODE;
                    description    
                "An FC switched to a lower priority (non-preferred) resource will not revert to a higher priority (preferred) resource when that recovers.";
                }
                identity RESILIENCE_CONTROL {
                    description    
                "none";
                }
                identity RESILIENCE_CONTROL_QUIESCENT {
                    base RESILIENCE_CONTROL;
                    description    
                "none";
                }
                identity RESILIENCE_CONTROL_RESTORING {
                    base RESILIENCE_CONTROL;
                    description    
                "none";
                }
                identity RESILIENCE_CONTROL_RECOVERY_FAILED {
                    base RESILIENCE_CONTROL;
                    description    
                "none";
                }
                identity RESILIENCE_CONTROL_UNKNOWN {
                    base RESILIENCE_CONTROL;
                    description    
                "none";
                }
                identity RUN_MODE {
                    description    
                "none";
                }
                identity RUN_MODE_FREE_RUN {
                    base RUN_MODE;
                    description    
                "The clock is not synchronized to another clock.";
                }
                identity RUN_MODE_LOCKED {
                    base RUN_MODE;
                    description    
                "The clock is synchronized to another clock.";
                }
                identity RUN_MODE_HOLD_OVER {
                    base RUN_MODE;
                    description    
                "The clock was previously synchronized to another clock but that timing input has been lost.
                        The clock is set to the last known synchronization.";
                }
                identity LAYER_PROTOCOL_NAME {
                    description    
                "none";
                }
                identity LAYER_PROTOCOL_NAME_PHOTONIC_MEDIA {
                    base LAYER_PROTOCOL_NAME;
                    description    
                "The characteristic information is that of a channel able to carry photons and of the photon source/sink.";
                }
                identity LAYER_PROTOCOL_NAME_OTU_AND_ODU {
                    base LAYER_PROTOCOL_NAME;
                    description    
                "The characteristic information is that of a channel able to carry ODU/OTU protocol (OTN) and of the ODU/OTU source/sink.";
                }
                identity LAYER_PROTOCOL_NAME_ETHERNET {
                    base LAYER_PROTOCOL_NAME;
                    description    
                "The characteristic information is that of a channel able to carry Ethernet protocol and of the Ethernet protocol source/sink.";
                }
                identity OPERATIONAL_STATE {
                    description    
                "none";
                }
                identity OPERATIONAL_STATE_DISABLED {
                    base OPERATIONAL_STATE;
                    description    
                "The resource is unable to meet the SLA of the user of the resource. 
                        If no (explicit) SLA is defined the resource is disabled if it is totally inoperable and unable to provide service to the user.";
                }
                identity OPERATIONAL_STATE_ENABLED {
                    base OPERATIONAL_STATE;
                    description    
                "The resource is partially or fully operable and available for use.";
                }
                identity ADMINISTRATIVE_STATE {
                    description    
                "none";
                }
                identity ADMINISTRATIVE_STATE_LOCKED {
                    base ADMINISTRATIVE_STATE;
                    description    
                "Users are administratively prohibited from making use of the resource.";
                }
                identity ADMINISTRATIVE_STATE_UNLOCKED {
                    base ADMINISTRATIVE_STATE;
                    description    
                "Users are allowed to use the resource.";
                }
                identity ADMINISTRATIVE_STATE_SHUTTING_DOWN {
                    base ADMINISTRATIVE_STATE;
                    description    
                "The entity is administratively restricted to existing instances of use only. There may be specific actions to remove existing uses. No new instances of use can be enabled.
                        The resource automatically transitions to “locked” when the last user quits. 
                        The administrative state is not visible in the client context. 
                        The lifecycle state “pending removal” should be used to indicate to the client that the provider intends to remove the resource.";
                }
                identity ADMINISTRATIVE_CONTROL {
                    description    
                "none";
                }
                identity ADMINISTRATIVE_CONTROL_UNLOCK {
                    base ADMINISTRATIVE_CONTROL;
                    description    
                "The intention is for the entity to become unlocked.
                        The entity may already be UNLOCKED.";
                }
                identity ADMINISTRATIVE_CONTROL_LOCK_PASSIVE {
                    base ADMINISTRATIVE_CONTROL;
                    description    
                "The intention is for the entity to become locked but no effort is expected to move to the Locked state (the state will be achieved once all users stop using the resource). 
                        The entity may be LOCKED.";
                }
                identity ADMINISTRATIVE_CONTROL_LOCK_ACTIVE {
                    base ADMINISTRATIVE_CONTROL;
                    description    
                "The intention is for the entity to become locked and it is expected that effort will be made to move to the Locked state (users will be actively removed). 
                        The entity may already be LOCKED.";
                }
                identity ADMINISTRATIVE_CONTROL_LOCK_IMMEDIATE {
                    base ADMINISTRATIVE_CONTROL;
                    description    
                "The intention is for the entity to become locked and it is expected to move to the Locked state immediately (users will be force removed). 
                        The entity may already be LOCKED.";
                }
                identity ADMINISTRATIVE_CONTROL_QUIESCENT {
                    base ADMINISTRATIVE_CONTROL;
                    description    
                "The administrative state is at a stable value (LOCKED/UNLOCKED) and no action is being taken.";
                }
                identity LIFECYCLE_STATE {
                    description    
                "none";
                }
                identity LIFECYCLE_STATE_PLANNED {
                    base LIFECYCLE_STATE;
                    description    
                "The resource is planned but is not present in the network.
                        Should include a 'time' when the resources are expected to be installed.";
                }
                identity LIFECYCLE_STATE_POTENTIAL_AVAILABLE {
                    base LIFECYCLE_STATE;
                    description    
                "The supporting resources are present in the network but are shared with other clients; or require further configuration before they can be used; or both.
                        (1) When a potential resource is configured and allocated to a client it is moved to the INSTALLED state for that client.
                        (2) If the potential resource has been consumed (e.g. allocated to another client) it is moved to the POTENTIAL BUSY state for all other clients.";
                }
                identity LIFECYCLE_STATE_POTENTIAL_BUSY {
                    base LIFECYCLE_STATE;
                    description    
                "The supporting resources are present in the network but have been allocated to other clients.";
                }
                identity LIFECYCLE_STATE_INSTALLED {
                    base LIFECYCLE_STATE;
                    description    
                "The resource is present in the network and is capable of providing the service.";
                }
                identity LIFECYCLE_STATE_PENDING_REMOVAL {
                    base LIFECYCLE_STATE;
                    description    
                "The resource has been marked for removal. Should include a “time” when the resources are expected to be removed.";
                }
                identity BLOCK_DIRECTION {
                    description    
                "none";
                }
                identity BLOCK_DIRECTION_NO_BLOCK {
                    base BLOCK_DIRECTION;
                    description    
                "The FC is not blocking signal related to the LTP.";
                }
                identity BLOCK_DIRECTION_INGRESS_BLOCK {
                    base BLOCK_DIRECTION;
                    description    
                "The FC is blocking signal that is flowing into the LTP from the FC.";
                }
                identity BLOCK_DIRECTION_EGRESS_BLOCK {
                    base BLOCK_DIRECTION;
                    description    
                "The FC is blocking signal flowing out of the LTP to the FC.";
                }
                identity BLOCK_DIRECTION_BIDIRECTIONAL_BLOCK {
                    base BLOCK_DIRECTION;
                    description    
                "The FC is blocking both directions of traffic, i.e. Ingress and Egress, to/from the LTP.";
                }
                identity CONNECTOR_AND_PIN_ORIENTATION {
                    description    
                "none";
                }
                identity CONNECTOR_AND_PIN_ORIENTATION_MALE {
                    base CONNECTOR_AND_PIN_ORIENTATION;
                    description    
                "The connecting elements are dominantly protrusions.";
                }
                identity CONNECTOR_AND_PIN_ORIENTATION_FEMALE {
                    base CONNECTOR_AND_PIN_ORIENTATION;
                    description    
                "The connecting elements are dominantly indentations.";
                }
                identity CONNECTOR_AND_PIN_ORIENTATION_SYMMETRIC_NEUTRAL {
                    base CONNECTOR_AND_PIN_ORIENTATION;
                    description    
                "The pin (and housing) orientation combination is such that it is symmetric so a connector is compatible with itself.
                        The connecting element may be a surface rather than protrusions or indentations.";
                }
                identity EQUIPMENT_CATEGORY {
                    description    
                "none";
                }
                identity EQUIPMENT_CATEGORY_SUBRACK {
                    base EQUIPMENT_CATEGORY;
                    description    
                "An assembly with holders designed to accommodate CIRCUIT_PACKs. 
                        The assembly is designed to be mounted in a RACK.";
                }
                identity EQUIPMENT_CATEGORY_CIRCUIT_PACK {
                    base EQUIPMENT_CATEGORY;
                    description    
                "An assembly with connectors compatible with those in a holder.
                        The assembly is designed to be mounted in a holder (SLOT) of a SUBRACK.
                        May also support holders (SLOTs) for SMALL_FORMFACTOR_PLUGGABLEs.";
                }
                identity EQUIPMENT_CATEGORY_SMALL_FORMFACTOR_PLUGGABLE {
                    base EQUIPMENT_CATEGORY;
                    description    
                "A small assembly (compared to a CIRCUIT_PACK) with connectors compatible with those in a holder.
                        The assembly is designed to be mounted in a holder (SLOT) of a CIRCUIT_PACK or STAND_ALONE_UNIT.";
                }
                identity EQUIPMENT_CATEGORY_STAND_ALONE_UNIT {
                    base EQUIPMENT_CATEGORY;
                    description    
                "An assembly with connectors for cabling and potentially with holders.
                        The assembly is designed to be mounted in a freeform environment (on a table or simple mechanical cabinet).
                        May support holders (SLOTs) for CIRCUIT_PACKs or for SMALL_FORMFACTOR_PLUGGABLEs.";
                }
                identity EQUIPMENT_CATEGORY_RACK {
                    base EQUIPMENT_CATEGORY;
                    description    
                "A mechanical assembly with cabling and predefined mounting points for particular SUBRACK types.
                        The assembly is designed to be mounted on the floor in a row with other RACKs.";
                }
                identity HOLDER_CATEGORY {
                    description    
                "none";
                }
                identity HOLDER_CATEGORY_SLOT {
                    base HOLDER_CATEGORY;
                    description    
                "A guided holder with fixed connectors.
                        The guided holder is designed to take a particular form of CIRCUIT_PACK or SMALL_FORMFACTOR_PLUGGABLE";
                }
                identity FORWARDING_RULE {
                    description    
                "none";
                }
                identity FORWARDING_RULE_CANNOT_FORWARD_ACROSS_FD_LINK {
                    base FORWARDING_RULE;
                    description    
                "LTPs referenced by the FD (or indirectly by the Link between FDs) cannot have FCs created between them.
                        This rule overrides all others.";
                }
                identity FORWARDING_RULE_MUST_FORWARD_ACROSS_FD_LINK {
                    base FORWARDING_RULE;
                    description    
                "LTPs referenced by the FD (or indirectly by the Link between FDs) MUST have FCs created between them.
                        This rule overrides all others except the CANNOT_FORWARD rule.";
                }
                identity FORWARDING_RULE_MAY_FORWARD_ACROSS_FD_LINK {
                    base FORWARDING_RULE;
                    description    
                "LTPs referenced by the FD (or indirectly by the Link between FDs) may have FCs created between them.
                        FCs may not be created between points that are not related by this rule either directly in an FD or indirectly via a Link linking two or more FDs.
                        For a Link points in an FD at one end of the Link can be connected to points in an FD at an other end of the Link.";
                }
                identity FORWARDING_RULE_NULL_FORWARDING_RULE {
                    base FORWARDING_RULE;
                    description    
                "none";
                }
                identity RULE_TYPE {
                    description    
                "none";
                }
                identity RULE_TYPE_FORWARDING {
                    base RULE_TYPE;
                    description    
                "The rule relates to creation of FCs.";
                }
                identity RULE_TYPE_COST {
                    base RULE_TYPE;
                    description    
                "The rule relates to forwarding cost.";
                }
                identity RULE_TYPE_RISK {
                    base RULE_TYPE;
                    description    
                "The rule relates to forwarding risk.";
                }
                identity RULE_TYPE_CAPACITY {
                    base RULE_TYPE;
                    description    
                "none";
                }
                identity PORT_ROLE_RULE_OPTION {
                    description    
                "none";
                }
                identity PORT_ROLE_RULE_OPTION_SAME_ROLE {
                    base PORT_ROLE_RULE_OPTION;
                    description    
                "The ports to which the rule applies must have role from the list in PortRole.";
                }
                identity PORT_ROLE_RULE_OPTION_DIFFERENT_ROLE {
                    base PORT_ROLE_RULE_OPTION;
                    description    
                "The ports to which the rule applies must not have a role from the list in PortRole.";
                }
                identity PORT_ROLE_RULE_OPTION_ANY_ROLE {
                    base PORT_ROLE_RULE_OPTION;
                    description    
                "The rule applies to any role of port.";
                }
                identity SIGNAL_PROPERTY_VALUE_RULE {
                    description    
                "none";
                }
                identity SIGNAL_PROPERTY_VALUE_RULE_SAME_VALUE {
                    base SIGNAL_PROPERTY_VALUE_RULE;
                    description    
                "none";
                }
                identity SIGNAL_PROPERTY_VALUE_RULE_ANY_VALUE {
                    base SIGNAL_PROPERTY_VALUE_RULE;
                    description    
                "none";
                }
                identity PARTNER {
                    description    
                "none";
                }
                identity PARTNER_FC {
                    base PARTNER;
                    description    
                "ForwardingConstruct.";
                }
                identity PARTNER_FD {
                    base PARTNER;
                    description    
                "ForwardingDomain.";
                }
                identity PARTNER_LINK {
                    base PARTNER;
                    description    
                "Link.";
                }
                identity PARTNER_CASC {
                    base PARTNER;
                    description    
                "ConfigurationAndSwitchController.";
                }
                identity PARTNER_CC {
                    base PARTNER;
                    description    
                "ControlConstruct.";
                }
                identity PARTNER_CD {
                    base PARTNER;
                    description    
                "ConstraintDomain.";
                }
                identity PARTNER_PC {
                    base PARTNER;
                    description    
                "ProcessingConstruct.";
                }
                identity PARTNER_PEER {
                    base PARTNER;
                    description    
                "LTP peer.";
                }
                identity PARTNER_CLIENT {
                    base PARTNER;
                    description    
                "LTP client.";
                }
                identity PARTNER_SERVER {
                    base PARTNER;
                    description    
                "LTP server.";
                }
                identity PARTNER_VIEW {
                    base PARTNER;
                    description    
                "LTP in other view.";
                }
                identity TASK_LIFECYCLE_STATE {
                    description    
                "none";
                }
                identity TASK_LIFECYCLE_STATE_RUNNING {
                    base TASK_LIFECYCLE_STATE;
                    description    
                "The task is running.";
                }
                identity TASK_LIFECYCLE_STATE_PAUSED {
                    base TASK_LIFECYCLE_STATE;
                    description    
                "The task has been paused.";
                }
                identity TASK_LIFECYCLE_STATE_WAITING {
                    base TASK_LIFECYCLE_STATE;
                    description    
                "The task is waiting for input etc.";
                }
                identity TASK_LIFECYCLE_STATE_ABORTING {
                    base TASK_LIFECYCLE_STATE;
                    description    
                "The task is aborting.";
                }
                identity TASK_LIFECYCLE_STATE_COMPLETED {
                    base TASK_LIFECYCLE_STATE;
                    description    
                "The task has been completed successfully.";
                }
                identity TASK_LIFECYCLE_STATE_ABORTED {
                    base TASK_LIFECYCLE_STATE;
                    description    
                "The task has been aborted.";
                }
                identity TASK_LIFECYCLE_STATE_ATTEMPTING_ROLLBACK {
                    base TASK_LIFECYCLE_STATE;
                    description    
                "The task is attempting to return the controlled system to a previous state.";
                }
                identity TASK_LIFECYCLE_STATE_ROLLBACK_COMPLETE {
                    base TASK_LIFECYCLE_STATE;
                    description    
                "The task has completed a roll back action.";
                }
                identity TASK_LIFECYCLE_STATE_ABANDONING {
                    base TASK_LIFECYCLE_STATE;
                    description    
                "Task is abandoning.";
                }
                identity TASK_LIFECYCLE_STATE_ABANDONED {
                    base TASK_LIFECYCLE_STATE;
                    description    
                "The task has been abandoned and is no longer running.";
                }
                identity TASK_LIFECYCLE_STATE_FAILED {
                    base TASK_LIFECYCLE_STATE;
                    description    
                "The task has failed.";
                }
                identity TASK_LIFECYCLE_STATE_ARCHIVED {
                    base TASK_LIFECYCLE_STATE;
                    description    
                "The task has been archived (and is no longer running).";
                }
                identity PROGRESS_STATUS {
                    description    
                "none";
                }
                identity PROGRESS_STATUS_COMPLETE {
                    base PROGRESS_STATUS;
                    description    
                "none";
                }
                identity PROGRESS_STATUS_IN_PROGRESS {
                    base PROGRESS_STATUS;
                    description    
                "none";
                }
                identity PROGRESS_STATUS_FAILED {
                    base PROGRESS_STATUS;
                    description    
                "none";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity.";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity.";
                }
                identity TERMINATION_DIRECTION_UNDEFINED_OR_UNKNOWN {
                    base TERMINATION_DIRECTION;
                    description    
                "Not a normal state. The system is unable to determine the correct value.";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base TERMINATION_DIRECTION;
                    description    
                "Not a normal state. The system is unable to determine the correct value.";
                }
                identity ACTION_VERBS {
                    description    
                "none";
                }
                identity ACTION_VERBS_CREATE_POST_ADD {
                    base ACTION_VERBS;
                    description    
                "none";
                }
                identity ACTION_VERBS_SET_UPDATE_PUT_MODIFY_WRITE_ADD {
                    base ACTION_VERBS;
                    description    
                "none";
                }
                identity ACTION_VERBS_GET_READ {
                    base ACTION_VERBS;
                    description    
                "none";
                }
                identity ACTION_VERBS_DELETE_REMOVE {
                    base ACTION_VERBS;
                    description    
                "none";
                }
                identity DIRECTION {
                    description    
                "none";
                }
                identity DIRECTION_IN {
                    base DIRECTION;
                    description    
                "none";
                }
                identity DIRECTION_OUT {
                    base DIRECTION;
                    description    
                "none";
                }
                identity DIRECTION_BIDIRECTIONAL {
                    base DIRECTION;
                    description    
                "none";
                }
                identity ACTION_VERBS {
                    description    
                "none";
                }
                identity ACTION_VERBS_CREATE_POST_ADD {
                    base ACTION_VERBS;
                    description    
                "Cause the addition of some structure.";
                }
                identity ACTION_VERBS_SET_UPDATE_PUT_MODIFY_WRITE_ADD {
                    base ACTION_VERBS;
                    description    
                "Cause the adjustment to some properties.";
                }
                identity ACTION_VERBS_GET_READ {
                    base ACTION_VERBS;
                    description    
                "Acquire information.";
                }
                identity ACTION_VERBS_DELETE_REMOVE {
                    base ACTION_VERBS;
                    description    
                "Eliminate some structure.";
                }
                identity ACTIVITY_DIRECTIVE {
                    description    
                "none";
                }
                identity ACTIVITY_DIRECTIVE_STRUCTURE_IS_NOT {
                    base ACTIVITY_DIRECTIVE;
                    description    
                "The structure defined should not be present. No part should be present (within the stated degrees of precision.";
                }
                identity ACTIVITY_DIRECTIVE_NEW_STRUCTURE_AND_VALUES {
                    base ACTIVITY_DIRECTIVE;
                    description    
                "None of the structure stated is expected to be present, but is required.";
                }
                identity ACTIVITY_DIRECTIVE_INCREMENTAL_STRUCTURE_AND_VALUES {
                    base ACTIVITY_DIRECTIVE;
                    description    
                "The structure stated is an increment on what already exists.
                        Increment in this case may also be decrement.";
                }
                identity ACTIVITY_DIRECTIVE_ONLY_VALUES_IN_EXISTING_STRUCTURE {
                    base ACTIVITY_DIRECTIVE;
                    description    
                "Only values should be modified, no new structure should be created and no structure should be deleted.";
                }
                identity ACTIVITY_DIRECTIVE_DEFINED_BY_VERB {
                    base ACTIVITY_DIRECTIVE;
                    description    
                "A verb is provided to give guidance (such as Create).";
                }
                identity ACTION_EFFORT {
                    description    
                "none";
                }
                identity ACTION_EFFORT_BEST_EFFORT {
                    base ACTION_EFFORT;
                    description    
                "none";
                }
                identity ACTION_EFFORT_EXACT_MATCH {
                    base ACTION_EFFORT;
                    description    
                "none";
                }
                identity PAUSE_RESUME_RULE {
                    description    
                "none";
                }
                identity PAUSE_RESUME_RULE_NO_PAUSE_POSSIBLE {
                    base PAUSE_RESUME_RULE;
                    description    
                "none";
                }
                grouping name-and-value {
                    leaf value-name {
                        type string;
                        description    
                    "The name of the value. The value need not have a name.";
                    }
                    leaf value {
                        type string;
                        description    
                    "The value.";
                    }
                    container name-and-value-authority {
                        uses name-and-value-authority;
                        description    
                "The authority that defines the named value.";
                    }
                    container global-class {
                        uses global-class;
                        description    
                "The scope of the name uniqueness.";
                    }
                    container local-class {
                        uses local-class;
                        description    
                "The scope of the name uniqueness.";
                    }
                    description    
                "A scoped name-value pair.";
                }
                grouping address {
                    leaf address-name {
                        type string;
                        description    
                    "The name of the address (to allow the specific hierarchy to be distinguished from others for the same entity).";
                    }
                    list address-element {
                        uses address-element;
                        description    
                "The elements of the address that form the recursive scope narrowing.";
                    }
                    description    
                "A description of location via a hierarchy of narrowing contexts.";
                }
                grouping local-id-and-class {
                    leaf class-of-instance {
                        type string;
                        description    
                    "The class to which the name refers.";
                    }
                    container local-id {
                        uses name-and-value;
                        description    
                "The localId of the entity.";
                    }
                    description    
                "The localId and the class of entity that it identifies.";
                }
                grouping name-and-class {
                    leaf class-of-instance {
                        type string;
                        description    
                    "The class to which the name refers.";
                    }
                    container name {
                        uses name-and-value;
                        description    
                "If the element is a name.";
                    }
                    description    
                "The name and the class of entity that it names.";
                }
                grouping address-element {
                    leaf address-element-name {
                        type string;
                        description    
                    "The name of the address element (e.g. 'shelf' as an element of a shelf/slot/port addressing scheme).
                            The remainder of the structure has the reference for the shelf.
";
                    }
                    container local-id {
                        uses local-id-and-class;
                        description    
                "If the element is a localId (where the element above in the hierarchy must be the context in which the specific localId is relevant).";
                    }
                    leaf uuid {
                        type universal-id;
                        description    
                    "If the element is a uuid (where this element could be the top of a hierarchy but may also be at some level in the hierarchy where address navigation is considered necessary to assist in location of the UUID).";
                    }
                    container name {
                        uses name-and-class;
                        description    
                "If the element is a name.";
                    }
                    container address {
                        uses address;
                        description    
                "none";
                    }
                    leaf arbitrary-element {
                        type string;
                        description    
                    "Where the element is from some external model that is not formally represented in this model.";
                    }
                    description    
                "One element of a hierarchy of elements.
                        Note that the element must have one and only one value chosen from a list of potential value types.";
                }


        /****************************************
        * package state-model
        **************************************/ 
            /****************************************
            * grouping statements for object classes
            **************************************/ 
                grouping state-pac {
                    leaf operational-state {
                        type operational-state;
                        config false;
                        description    
                    "The operational state is used to indicate whether or not the resource is installed and working.";
                    }
                    leaf administrative-control {
                        type administrative-control;
                        description    
                    "The administrativeControl state provides control of the availability of specific resources without modification to the provisioning of those resources.
                            The value is the current control target. The actual administrativeState may or may not be at target.";
                    }
                    leaf administrative-state {
                        type administrative-state;
                        config false;
                        description    
                    "Shows whether or not the client has permission to use or has a prohibition against using the resource.
                            The administrative state expresses usage permissions for specific resources without modification to the provisioning of those resources.";
                    }
                    leaf lifecycle-state {
                        type lifecycle-state;
                        description    
                    "Used to track the planned deployment, allocation to clients and withdrawal of resources.";
                    }
                    description    
                "Provides general state attributes.";
                }

/****************************************
* typedef statements
**************************************/ 
                typedef operational-state {
                    type identityref {
                        base OPERATIONAL_STATE;
                    }
                    description    
                "The operational state is used to indicate whether or not the resource is installed and working. ";
                }
                typedef administrative-state {
                    type identityref {
                        base ADMINISTRATIVE_STATE;
                    }
                    description    
                "The administrative state is used to show whether use of a resource is allowed or prohibited.
                        The administrative state can be observed and directly controlled by certain operational roles. 
                        Typically, only a user (in the provider context) with administrative privileges is allowed to write the administrative state, any other users are restricted to read only.";
                }
                typedef administrative-control {
                    type identityref {
                        base ADMINISTRATIVE_CONTROL;
                    }
                    description    
                "Reflects the current control action when the entity is not in the desired state.";
                }
                typedef lifecycle-state {
                    type identityref {
                        base LIFECYCLE_STATE;
                    }
                    description    
                "This state is used to track the planned deployment, allocation to clients and withdrawal of resources.";
                }

/*********************************************
* grouping statements for complex data types
*******************************************/ 
                identity PORT_DIRECTION {
                    description    
                "none";
                }
                identity PORT_DIRECTION_BIDIRECTIONAL {
                    base PORT_DIRECTION;
                    description    
                "The Port has both an INPUT flow and an OUTPUT flow defined.";
                }
                identity PORT_DIRECTION_INPUT {
                    base PORT_DIRECTION;
                    description    
                "The Port only has definition for a flow into the Forwarding entity (i.e. an ingress flow).";
                }
                identity PORT_DIRECTION_OUTPUT {
                    base PORT_DIRECTION;
                    description    
                "The Port only has definition for a flow out of the Forwarding entity (i.e. an egress flow).";
                }
                identity PORT_DIRECTION_UNIDENTIFIED_OR_UNKNOWN {
                    base PORT_DIRECTION;
                    description    
                "Not a normal state. The system is unable to determine the correct value.";
                }
                identity PORT_DIRECTION_OMNIDIRECTIONAL {
                    base PORT_DIRECTION;
                    description    
                "none";
                }
                identity FORWARDING_DIRECTION {
                    description    
                "none";
                }
                identity FORWARDING_DIRECTION_BIDIRECTIONAL {
                    base FORWARDING_DIRECTION;
                    description    
                "The Forwarding entity supports both BIDIRECTIONAL flows at all Ports (i.e. all Ports have both an INPUT flow and an OUTPUT flow defined).";
                }
                identity FORWARDING_DIRECTION_UNIDIRECTIONAL {
                    base FORWARDING_DIRECTION;
                    description    
                "The Forwarding entity has Ports that are either INPUT or OUTPUT. It has no BIDIRECTIONAL Ports.";
                }
                identity FORWARDING_DIRECTION_UNDEFINED_OR_UNKNOWN {
                    base FORWARDING_DIRECTION;
                    description    
                "Not a normal state. The system is unable to determine the correct value.";
                }
                identity FORWARDING_DIRECTION_OMNIDIRECTIONAL {
                    base FORWARDING_DIRECTION;
                    description    
                "none";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base TERMINATION_DIRECTION;
                    description    
                "Not a normal state. The system is unable to determine the correct value.";
                }
                identity EXTENDED_TERMINATION_DIRECTION {
                    description    
                "none";
                }
                identity EXTENDED_TERMINATION_DIRECTION_CONTRA_DIRECTION_SINK {
                    base EXTENDED_TERMINATION_DIRECTION;
                    description    
                "The essential flow of the Termination entity is SINK (i.e. up the layer stack) but the INPUT flow of the Termination entity was provided by a SOURCE OUTPUT or taken from a SOURCE INPUT (duplicating the input signal) hence reversing the flow orientation from down the layer stack to up the layer stack.";
                }
                identity EXTENDED_TERMINATION_DIRECTION_CONTRA_DIRECTION_SOURCE {
                    base EXTENDED_TERMINATION_DIRECTION;
                    description    
                "The essential flow of the Termination entity is SOURCE (i.e. down the layer stack) but the OUTPUT flow of the Termination entity was fed to (and replaces) a SINK OUTPUT or was fed to a SINK INPUT (replacing the normal flow) hence reversing the flow orientation from down the layer stack to up the layer stack.";
                }
                identity TERMINATION_STATE {
                    description    
                "none";
                }
                identity TERMINATION_STATE_LP_CAN_NEVER_TERMINATE {
                    base TERMINATION_STATE;
                    description    
                "A non-flexible case that can never be terminated.";
                }
                identity TERMINATION_STATE_LP_NOT_TERMINATED {
                    base TERMINATION_STATE;
                    description    
                "A flexible termination that can terminate but is currently not terminated.";
                }
                identity TERMINATION_STATE_TERMINATED_SERVER_TO_CLIENT_FLOW {
                    base TERMINATION_STATE;
                    description    
                "A flexible termination that is currently terminated for server to client flow only.";
                }
                identity TERMINATION_STATE_TERMINATED_CLIENT_TO_SERVER_FLOW {
                    base TERMINATION_STATE;
                    description    
                "A flexible termination that is currently terminated for client to server flow only.";
                }
                identity TERMINATION_STATE_TERMINATED_BIDIRECTIONAL {
                    base TERMINATION_STATE;
                    description    
                "A flexible termination that is currently terminated in both directions of flow.";
                }
                identity TERMINATION_STATE_LP_PERMENANTLY_TERMINATED {
                    base TERMINATION_STATE;
                    description    
                "A non-flexible termination that is always terminated (in both directions of flow for a bidirectional case and in the one direction of flow for both unidirectional cases).";
                }
                identity TERMINATION_STATE_TERMINATION_STATE_UNKNOWN {
                    base TERMINATION_STATE;
                    description    
                "There TerminationState cannot be determined.";
                }
                identity PROTECTION_REASON {
                    description    
                "none";
                }
                identity PROTECTION_REASON_WAIT_TO_REVERT {
                    base PROTECTION_REASON;
                    description    
                "The resource is selected as control is waiting to restore to a preferred resource.";
                }
                identity PROTECTION_REASON_SIGNAL_DEGRADE {
                    base PROTECTION_REASON;
                    description    
                "The resource is selected as the best preferred resource is in signal degrade.";
                }
                identity PROTECTION_REASON_SIGNAL_FAIL {
                    base PROTECTION_REASON;
                    description    
                "The resource is selected as the best preferred resource is in signal fail.";
                }
                identity ROUTE_SELECTION_CONTROL {
                    description    
                "none";
                }
                identity ROUTE_SELECTION_CONTROL_LOCK_OUT {
                    base ROUTE_SELECTION_CONTROL;
                    description    
                "The resource is configured to temporarily not be available for use in the protection scheme(s) it is part of.
                        This overrides all other protection control states including forced.
                        If the item is locked out, then it cannot be used under any circumstances.
                        Note: Only relevant when part of a protection scheme.
                        Note: if a protection process that has a relationship to the item (i.e. is one of the options the protection process may choose) is deactivated by being isFrozen = true) then the lockout request will be rejected. ";
                }
                identity ROUTE_SELECTION_REASON {
                    description    
                "none";
                }
                identity SWITCH_CONTROL {
                    description    
                "none";
                }
                identity SWITCH_CONTROL_NORMAL {
                    base SWITCH_CONTROL;
                    description    
                "No administrative control applied to the switch.";
                }
                identity SWITCH_CONTROL_MANUAL {
                    base SWITCH_CONTROL;
                    description    
                "Resource temporarily chosen by control configuration where the resource is not the preferred resource.
                        Preferred resource has highest priority.
                        Temporarily overrides reversion.
                        If this resource fails, it will switch to best available resource. 
                        If resource selected is shared and another FC requires the resource, then the selection control will change to Normal and switch to best available based upon normal rules.
                        Cannot manually switch a Forced switch, cannot remove a forced switch, cannot switch to a locked out item and will be rejected if the protection process is deactivated by being Freeze = true).
                        A manual switch/route that is selecting an FcPort, LTP, FC, Link or Route that is subsequently set to LOCK_OUT will have the manual removed (changed to NORMAL) and will switch away from the FcPort with LOCK_OUT to best available based upon normal rules.
                        A manual switch that is selecting an FcPort that is subsequently selected by a Forced switch will be restored to normal operation and the manual will be removed.
                        A manual switch/route that is selecting an FcPort, LTP, FC, Link or Route that is subsequently manual selected by another switch/route will have the manual removed and will switch away from the FcPort.
                        Can be returned to NORMAL by configuration action.";
                }
                identity SWITCH_CONTROL_FORCED {
                    base SWITCH_CONTROL;
                    description    
                "Resource temporarily chosen by control configuration where the resource is not the preferred resource.
                        Preferred resource has highest priority.
                        Temporarily overrides reversion.
                        If this resource fails it will NOT switch. 
                        If resource selected is shared and another FC requires the resource through a FORCE on that FC and the FC is of a higher FcPriority then the selection control on this FC will change to NORMAL and switch to best available based upon normal rules.
                        If the resource selected is then set to LOCK_OUT then the selection control will change to NORMAL and switch to best available based upon normal rules.
                        Can be returned to NORMAL by configuration action.";
                }
                identity SWITCH_STATE_REASON {
                    description    
                "none";
                }
                identity REVERSION_MODE {
                    description    
                "none";
                }
                identity REVERSION_MODE_REVERTIVE {
                    base REVERSION_MODE;
                    description    
                "An FC switched to a lower priority (non-preferred) resource will revert to a higher priority (preferred) resource when that recovers (potentially after some hold-off time).";
                }
                identity REVERSION_MODE_NON-REVERTIVE {
                    base REVERSION_MODE;
                    description    
                "An FC switched to a lower priority (non-preferred) resource will not revert to a higher priority (preferred) resource when that recovers.";
                }
                identity RESILIENCE_CONTROL {
                    description    
                "none";
                }
                identity RESILIENCE_CONTROL_QUIESCENT {
                    base RESILIENCE_CONTROL;
                    description    
                "none";
                }
                identity RESILIENCE_CONTROL_RESTORING {
                    base RESILIENCE_CONTROL;
                    description    
                "none";
                }
                identity RESILIENCE_CONTROL_RECOVERY_FAILED {
                    base RESILIENCE_CONTROL;
                    description    
                "none";
                }
                identity RESILIENCE_CONTROL_UNKNOWN {
                    base RESILIENCE_CONTROL;
                    description    
                "none";
                }
                identity RUN_MODE {
                    description    
                "none";
                }
                identity RUN_MODE_FREE_RUN {
                    base RUN_MODE;
                    description    
                "The clock is not synchronized to another clock.";
                }
                identity RUN_MODE_LOCKED {
                    base RUN_MODE;
                    description    
                "The clock is synchronized to another clock.";
                }
                identity RUN_MODE_HOLD_OVER {
                    base RUN_MODE;
                    description    
                "The clock was previously synchronized to another clock but that timing input has been lost.
                        The clock is set to the last known synchronization.";
                }
                identity LAYER_PROTOCOL_NAME {
                    description    
                "none";
                }
                identity LAYER_PROTOCOL_NAME_PHOTONIC_MEDIA {
                    base LAYER_PROTOCOL_NAME;
                    description    
                "The characteristic information is that of a channel able to carry photons and of the photon source/sink.";
                }
                identity LAYER_PROTOCOL_NAME_OTU_AND_ODU {
                    base LAYER_PROTOCOL_NAME;
                    description    
                "The characteristic information is that of a channel able to carry ODU/OTU protocol (OTN) and of the ODU/OTU source/sink.";
                }
                identity LAYER_PROTOCOL_NAME_ETHERNET {
                    base LAYER_PROTOCOL_NAME;
                    description    
                "The characteristic information is that of a channel able to carry Ethernet protocol and of the Ethernet protocol source/sink.";
                }
                identity OPERATIONAL_STATE {
                    description    
                "none";
                }
                identity OPERATIONAL_STATE_DISABLED {
                    base OPERATIONAL_STATE;
                    description    
                "The resource is unable to meet the SLA of the user of the resource. 
                        If no (explicit) SLA is defined the resource is disabled if it is totally inoperable and unable to provide service to the user.";
                }
                identity OPERATIONAL_STATE_ENABLED {
                    base OPERATIONAL_STATE;
                    description    
                "The resource is partially or fully operable and available for use.";
                }
                identity ADMINISTRATIVE_STATE {
                    description    
                "none";
                }
                identity ADMINISTRATIVE_STATE_LOCKED {
                    base ADMINISTRATIVE_STATE;
                    description    
                "Users are administratively prohibited from making use of the resource.";
                }
                identity ADMINISTRATIVE_STATE_UNLOCKED {
                    base ADMINISTRATIVE_STATE;
                    description    
                "Users are allowed to use the resource.";
                }
                identity ADMINISTRATIVE_STATE_SHUTTING_DOWN {
                    base ADMINISTRATIVE_STATE;
                    description    
                "The entity is administratively restricted to existing instances of use only. There may be specific actions to remove existing uses. No new instances of use can be enabled.
                        The resource automatically transitions to “locked” when the last user quits. 
                        The administrative state is not visible in the client context. 
                        The lifecycle state “pending removal” should be used to indicate to the client that the provider intends to remove the resource.";
                }
                identity ADMINISTRATIVE_CONTROL {
                    description    
                "none";
                }
                identity ADMINISTRATIVE_CONTROL_UNLOCK {
                    base ADMINISTRATIVE_CONTROL;
                    description    
                "The intention is for the entity to become unlocked.
                        The entity may already be UNLOCKED.";
                }
                identity ADMINISTRATIVE_CONTROL_LOCK_PASSIVE {
                    base ADMINISTRATIVE_CONTROL;
                    description    
                "The intention is for the entity to become locked but no effort is expected to move to the Locked state (the state will be achieved once all users stop using the resource). 
                        The entity may be LOCKED.";
                }
                identity ADMINISTRATIVE_CONTROL_LOCK_ACTIVE {
                    base ADMINISTRATIVE_CONTROL;
                    description    
                "The intention is for the entity to become locked and it is expected that effort will be made to move to the Locked state (users will be actively removed). 
                        The entity may already be LOCKED.";
                }
                identity ADMINISTRATIVE_CONTROL_LOCK_IMMEDIATE {
                    base ADMINISTRATIVE_CONTROL;
                    description    
                "The intention is for the entity to become locked and it is expected to move to the Locked state immediately (users will be force removed). 
                        The entity may already be LOCKED.";
                }
                identity ADMINISTRATIVE_CONTROL_QUIESCENT {
                    base ADMINISTRATIVE_CONTROL;
                    description    
                "The administrative state is at a stable value (LOCKED/UNLOCKED) and no action is being taken.";
                }
                identity LIFECYCLE_STATE {
                    description    
                "none";
                }
                identity LIFECYCLE_STATE_PLANNED {
                    base LIFECYCLE_STATE;
                    description    
                "The resource is planned but is not present in the network.
                        Should include a 'time' when the resources are expected to be installed.";
                }
                identity LIFECYCLE_STATE_POTENTIAL_AVAILABLE {
                    base LIFECYCLE_STATE;
                    description    
                "The supporting resources are present in the network but are shared with other clients; or require further configuration before they can be used; or both.
                        (1) When a potential resource is configured and allocated to a client it is moved to the INSTALLED state for that client.
                        (2) If the potential resource has been consumed (e.g. allocated to another client) it is moved to the POTENTIAL BUSY state for all other clients.";
                }
                identity LIFECYCLE_STATE_POTENTIAL_BUSY {
                    base LIFECYCLE_STATE;
                    description    
                "The supporting resources are present in the network but have been allocated to other clients.";
                }
                identity LIFECYCLE_STATE_INSTALLED {
                    base LIFECYCLE_STATE;
                    description    
                "The resource is present in the network and is capable of providing the service.";
                }
                identity LIFECYCLE_STATE_PENDING_REMOVAL {
                    base LIFECYCLE_STATE;
                    description    
                "The resource has been marked for removal. Should include a “time” when the resources are expected to be removed.";
                }
                identity BLOCK_DIRECTION {
                    description    
                "none";
                }
                identity BLOCK_DIRECTION_NO_BLOCK {
                    base BLOCK_DIRECTION;
                    description    
                "The FC is not blocking signal related to the LTP.";
                }
                identity BLOCK_DIRECTION_INGRESS_BLOCK {
                    base BLOCK_DIRECTION;
                    description    
                "The FC is blocking signal that is flowing into the LTP from the FC.";
                }
                identity BLOCK_DIRECTION_EGRESS_BLOCK {
                    base BLOCK_DIRECTION;
                    description    
                "The FC is blocking signal flowing out of the LTP to the FC.";
                }
                identity BLOCK_DIRECTION_BIDIRECTIONAL_BLOCK {
                    base BLOCK_DIRECTION;
                    description    
                "The FC is blocking both directions of traffic, i.e. Ingress and Egress, to/from the LTP.";
                }
                identity CONNECTOR_AND_PIN_ORIENTATION {
                    description    
                "none";
                }
                identity CONNECTOR_AND_PIN_ORIENTATION_MALE {
                    base CONNECTOR_AND_PIN_ORIENTATION;
                    description    
                "The connecting elements are dominantly protrusions.";
                }
                identity CONNECTOR_AND_PIN_ORIENTATION_FEMALE {
                    base CONNECTOR_AND_PIN_ORIENTATION;
                    description    
                "The connecting elements are dominantly indentations.";
                }
                identity CONNECTOR_AND_PIN_ORIENTATION_SYMMETRIC_NEUTRAL {
                    base CONNECTOR_AND_PIN_ORIENTATION;
                    description    
                "The pin (and housing) orientation combination is such that it is symmetric so a connector is compatible with itself.
                        The connecting element may be a surface rather than protrusions or indentations.";
                }
                identity EQUIPMENT_CATEGORY {
                    description    
                "none";
                }
                identity EQUIPMENT_CATEGORY_SUBRACK {
                    base EQUIPMENT_CATEGORY;
                    description    
                "An assembly with holders designed to accommodate CIRCUIT_PACKs. 
                        The assembly is designed to be mounted in a RACK.";
                }
                identity EQUIPMENT_CATEGORY_CIRCUIT_PACK {
                    base EQUIPMENT_CATEGORY;
                    description    
                "An assembly with connectors compatible with those in a holder.
                        The assembly is designed to be mounted in a holder (SLOT) of a SUBRACK.
                        May also support holders (SLOTs) for SMALL_FORMFACTOR_PLUGGABLEs.";
                }
                identity EQUIPMENT_CATEGORY_SMALL_FORMFACTOR_PLUGGABLE {
                    base EQUIPMENT_CATEGORY;
                    description    
                "A small assembly (compared to a CIRCUIT_PACK) with connectors compatible with those in a holder.
                        The assembly is designed to be mounted in a holder (SLOT) of a CIRCUIT_PACK or STAND_ALONE_UNIT.";
                }
                identity EQUIPMENT_CATEGORY_STAND_ALONE_UNIT {
                    base EQUIPMENT_CATEGORY;
                    description    
                "An assembly with connectors for cabling and potentially with holders.
                        The assembly is designed to be mounted in a freeform environment (on a table or simple mechanical cabinet).
                        May support holders (SLOTs) for CIRCUIT_PACKs or for SMALL_FORMFACTOR_PLUGGABLEs.";
                }
                identity EQUIPMENT_CATEGORY_RACK {
                    base EQUIPMENT_CATEGORY;
                    description    
                "A mechanical assembly with cabling and predefined mounting points for particular SUBRACK types.
                        The assembly is designed to be mounted on the floor in a row with other RACKs.";
                }
                identity HOLDER_CATEGORY {
                    description    
                "none";
                }
                identity HOLDER_CATEGORY_SLOT {
                    base HOLDER_CATEGORY;
                    description    
                "A guided holder with fixed connectors.
                        The guided holder is designed to take a particular form of CIRCUIT_PACK or SMALL_FORMFACTOR_PLUGGABLE";
                }
                identity FORWARDING_RULE {
                    description    
                "none";
                }
                identity FORWARDING_RULE_CANNOT_FORWARD_ACROSS_FD_LINK {
                    base FORWARDING_RULE;
                    description    
                "LTPs referenced by the FD (or indirectly by the Link between FDs) cannot have FCs created between them.
                        This rule overrides all others.";
                }
                identity FORWARDING_RULE_MUST_FORWARD_ACROSS_FD_LINK {
                    base FORWARDING_RULE;
                    description    
                "LTPs referenced by the FD (or indirectly by the Link between FDs) MUST have FCs created between them.
                        This rule overrides all others except the CANNOT_FORWARD rule.";
                }
                identity FORWARDING_RULE_MAY_FORWARD_ACROSS_FD_LINK {
                    base FORWARDING_RULE;
                    description    
                "LTPs referenced by the FD (or indirectly by the Link between FDs) may have FCs created between them.
                        FCs may not be created between points that are not related by this rule either directly in an FD or indirectly via a Link linking two or more FDs.
                        For a Link points in an FD at one end of the Link can be connected to points in an FD at an other end of the Link.";
                }
                identity FORWARDING_RULE_NULL_FORWARDING_RULE {
                    base FORWARDING_RULE;
                    description    
                "none";
                }
                identity RULE_TYPE {
                    description    
                "none";
                }
                identity RULE_TYPE_FORWARDING {
                    base RULE_TYPE;
                    description    
                "The rule relates to creation of FCs.";
                }
                identity RULE_TYPE_COST {
                    base RULE_TYPE;
                    description    
                "The rule relates to forwarding cost.";
                }
                identity RULE_TYPE_RISK {
                    base RULE_TYPE;
                    description    
                "The rule relates to forwarding risk.";
                }
                identity RULE_TYPE_CAPACITY {
                    base RULE_TYPE;
                    description    
                "none";
                }
                identity PORT_ROLE_RULE_OPTION {
                    description    
                "none";
                }
                identity PORT_ROLE_RULE_OPTION_SAME_ROLE {
                    base PORT_ROLE_RULE_OPTION;
                    description    
                "The ports to which the rule applies must have role from the list in PortRole.";
                }
                identity PORT_ROLE_RULE_OPTION_DIFFERENT_ROLE {
                    base PORT_ROLE_RULE_OPTION;
                    description    
                "The ports to which the rule applies must not have a role from the list in PortRole.";
                }
                identity PORT_ROLE_RULE_OPTION_ANY_ROLE {
                    base PORT_ROLE_RULE_OPTION;
                    description    
                "The rule applies to any role of port.";
                }
                identity SIGNAL_PROPERTY_VALUE_RULE {
                    description    
                "none";
                }
                identity SIGNAL_PROPERTY_VALUE_RULE_SAME_VALUE {
                    base SIGNAL_PROPERTY_VALUE_RULE;
                    description    
                "none";
                }
                identity SIGNAL_PROPERTY_VALUE_RULE_ANY_VALUE {
                    base SIGNAL_PROPERTY_VALUE_RULE;
                    description    
                "none";
                }
                identity PARTNER {
                    description    
                "none";
                }
                identity PARTNER_FC {
                    base PARTNER;
                    description    
                "ForwardingConstruct.";
                }
                identity PARTNER_FD {
                    base PARTNER;
                    description    
                "ForwardingDomain.";
                }
                identity PARTNER_LINK {
                    base PARTNER;
                    description    
                "Link.";
                }
                identity PARTNER_CASC {
                    base PARTNER;
                    description    
                "ConfigurationAndSwitchController.";
                }
                identity PARTNER_CC {
                    base PARTNER;
                    description    
                "ControlConstruct.";
                }
                identity PARTNER_CD {
                    base PARTNER;
                    description    
                "ConstraintDomain.";
                }
                identity PARTNER_PC {
                    base PARTNER;
                    description    
                "ProcessingConstruct.";
                }
                identity PARTNER_PEER {
                    base PARTNER;
                    description    
                "LTP peer.";
                }
                identity PARTNER_CLIENT {
                    base PARTNER;
                    description    
                "LTP client.";
                }
                identity PARTNER_SERVER {
                    base PARTNER;
                    description    
                "LTP server.";
                }
                identity PARTNER_VIEW {
                    base PARTNER;
                    description    
                "LTP in other view.";
                }
                identity TASK_LIFECYCLE_STATE {
                    description    
                "none";
                }
                identity TASK_LIFECYCLE_STATE_RUNNING {
                    base TASK_LIFECYCLE_STATE;
                    description    
                "The task is running.";
                }
                identity TASK_LIFECYCLE_STATE_PAUSED {
                    base TASK_LIFECYCLE_STATE;
                    description    
                "The task has been paused.";
                }
                identity TASK_LIFECYCLE_STATE_WAITING {
                    base TASK_LIFECYCLE_STATE;
                    description    
                "The task is waiting for input etc.";
                }
                identity TASK_LIFECYCLE_STATE_ABORTING {
                    base TASK_LIFECYCLE_STATE;
                    description    
                "The task is aborting.";
                }
                identity TASK_LIFECYCLE_STATE_COMPLETED {
                    base TASK_LIFECYCLE_STATE;
                    description    
                "The task has been completed successfully.";
                }
                identity TASK_LIFECYCLE_STATE_ABORTED {
                    base TASK_LIFECYCLE_STATE;
                    description    
                "The task has been aborted.";
                }
                identity TASK_LIFECYCLE_STATE_ATTEMPTING_ROLLBACK {
                    base TASK_LIFECYCLE_STATE;
                    description    
                "The task is attempting to return the controlled system to a previous state.";
                }
                identity TASK_LIFECYCLE_STATE_ROLLBACK_COMPLETE {
                    base TASK_LIFECYCLE_STATE;
                    description    
                "The task has completed a roll back action.";
                }
                identity TASK_LIFECYCLE_STATE_ABANDONING {
                    base TASK_LIFECYCLE_STATE;
                    description    
                "Task is abandoning.";
                }
                identity TASK_LIFECYCLE_STATE_ABANDONED {
                    base TASK_LIFECYCLE_STATE;
                    description    
                "The task has been abandoned and is no longer running.";
                }
                identity TASK_LIFECYCLE_STATE_FAILED {
                    base TASK_LIFECYCLE_STATE;
                    description    
                "The task has failed.";
                }
                identity TASK_LIFECYCLE_STATE_ARCHIVED {
                    base TASK_LIFECYCLE_STATE;
                    description    
                "The task has been archived (and is no longer running).";
                }
                identity PROGRESS_STATUS {
                    description    
                "none";
                }
                identity PROGRESS_STATUS_COMPLETE {
                    base PROGRESS_STATUS;
                    description    
                "none";
                }
                identity PROGRESS_STATUS_IN_PROGRESS {
                    base PROGRESS_STATUS;
                    description    
                "none";
                }
                identity PROGRESS_STATUS_FAILED {
                    base PROGRESS_STATUS;
                    description    
                "none";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity.";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity.";
                }
                identity TERMINATION_DIRECTION_UNDEFINED_OR_UNKNOWN {
                    base TERMINATION_DIRECTION;
                    description    
                "Not a normal state. The system is unable to determine the correct value.";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base TERMINATION_DIRECTION;
                    description    
                "Not a normal state. The system is unable to determine the correct value.";
                }
                identity ACTION_VERBS {
                    description    
                "none";
                }
                identity ACTION_VERBS_CREATE_POST_ADD {
                    base ACTION_VERBS;
                    description    
                "none";
                }
                identity ACTION_VERBS_SET_UPDATE_PUT_MODIFY_WRITE_ADD {
                    base ACTION_VERBS;
                    description    
                "none";
                }
                identity ACTION_VERBS_GET_READ {
                    base ACTION_VERBS;
                    description    
                "none";
                }
                identity ACTION_VERBS_DELETE_REMOVE {
                    base ACTION_VERBS;
                    description    
                "none";
                }
                identity DIRECTION {
                    description    
                "none";
                }
                identity DIRECTION_IN {
                    base DIRECTION;
                    description    
                "none";
                }
                identity DIRECTION_OUT {
                    base DIRECTION;
                    description    
                "none";
                }
                identity DIRECTION_BIDIRECTIONAL {
                    base DIRECTION;
                    description    
                "none";
                }
                identity ACTION_VERBS {
                    description    
                "none";
                }
                identity ACTION_VERBS_CREATE_POST_ADD {
                    base ACTION_VERBS;
                    description    
                "Cause the addition of some structure.";
                }
                identity ACTION_VERBS_SET_UPDATE_PUT_MODIFY_WRITE_ADD {
                    base ACTION_VERBS;
                    description    
                "Cause the adjustment to some properties.";
                }
                identity ACTION_VERBS_GET_READ {
                    base ACTION_VERBS;
                    description    
                "Acquire information.";
                }
                identity ACTION_VERBS_DELETE_REMOVE {
                    base ACTION_VERBS;
                    description    
                "Eliminate some structure.";
                }
                identity ACTIVITY_DIRECTIVE {
                    description    
                "none";
                }
                identity ACTIVITY_DIRECTIVE_STRUCTURE_IS_NOT {
                    base ACTIVITY_DIRECTIVE;
                    description    
                "The structure defined should not be present. No part should be present (within the stated degrees of precision.";
                }
                identity ACTIVITY_DIRECTIVE_NEW_STRUCTURE_AND_VALUES {
                    base ACTIVITY_DIRECTIVE;
                    description    
                "None of the structure stated is expected to be present, but is required.";
                }
                identity ACTIVITY_DIRECTIVE_INCREMENTAL_STRUCTURE_AND_VALUES {
                    base ACTIVITY_DIRECTIVE;
                    description    
                "The structure stated is an increment on what already exists.
                        Increment in this case may also be decrement.";
                }
                identity ACTIVITY_DIRECTIVE_ONLY_VALUES_IN_EXISTING_STRUCTURE {
                    base ACTIVITY_DIRECTIVE;
                    description    
                "Only values should be modified, no new structure should be created and no structure should be deleted.";
                }
                identity ACTIVITY_DIRECTIVE_DEFINED_BY_VERB {
                    base ACTIVITY_DIRECTIVE;
                    description    
                "A verb is provided to give guidance (such as Create).";
                }
                identity ACTION_EFFORT {
                    description    
                "none";
                }
                identity ACTION_EFFORT_BEST_EFFORT {
                    base ACTION_EFFORT;
                    description    
                "none";
                }
                identity ACTION_EFFORT_EXACT_MATCH {
                    base ACTION_EFFORT;
                    description    
                "none";
                }
                identity PAUSE_RESUME_RULE {
                    description    
                "none";
                }
                identity PAUSE_RESUME_RULE_NO_PAUSE_POSSIBLE {
                    base PAUSE_RESUME_RULE;
                    description    
                "none";
                }

            /****************************************
            * package state-machines
            **************************************/ 



    /****************************************
    * package core-model-enhancements
    **************************************/ 
        /****************************************
        * package fc-switch-enhancements-developed
        **************************************/ 
/****************************************
* typedef statements
**************************************/ 
                typedef block-direction {
                    type identityref {
                        base BLOCK_DIRECTION;
                    }
                    description    
                "Provides the potential signal blocking modes.";
                }

/*********************************************
* grouping statements for complex data types
*******************************************/ 
                identity PORT_DIRECTION {
                    description    
                "none";
                }
                identity PORT_DIRECTION_BIDIRECTIONAL {
                    base PORT_DIRECTION;
                    description    
                "The Port has both an INPUT flow and an OUTPUT flow defined.";
                }
                identity PORT_DIRECTION_INPUT {
                    base PORT_DIRECTION;
                    description    
                "The Port only has definition for a flow into the Forwarding entity (i.e. an ingress flow).";
                }
                identity PORT_DIRECTION_OUTPUT {
                    base PORT_DIRECTION;
                    description    
                "The Port only has definition for a flow out of the Forwarding entity (i.e. an egress flow).";
                }
                identity PORT_DIRECTION_UNIDENTIFIED_OR_UNKNOWN {
                    base PORT_DIRECTION;
                    description    
                "Not a normal state. The system is unable to determine the correct value.";
                }
                identity PORT_DIRECTION_OMNIDIRECTIONAL {
                    base PORT_DIRECTION;
                    description    
                "none";
                }
                identity FORWARDING_DIRECTION {
                    description    
                "none";
                }
                identity FORWARDING_DIRECTION_BIDIRECTIONAL {
                    base FORWARDING_DIRECTION;
                    description    
                "The Forwarding entity supports both BIDIRECTIONAL flows at all Ports (i.e. all Ports have both an INPUT flow and an OUTPUT flow defined).";
                }
                identity FORWARDING_DIRECTION_UNIDIRECTIONAL {
                    base FORWARDING_DIRECTION;
                    description    
                "The Forwarding entity has Ports that are either INPUT or OUTPUT. It has no BIDIRECTIONAL Ports.";
                }
                identity FORWARDING_DIRECTION_UNDEFINED_OR_UNKNOWN {
                    base FORWARDING_DIRECTION;
                    description    
                "Not a normal state. The system is unable to determine the correct value.";
                }
                identity FORWARDING_DIRECTION_OMNIDIRECTIONAL {
                    base FORWARDING_DIRECTION;
                    description    
                "none";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base TERMINATION_DIRECTION;
                    description    
                "Not a normal state. The system is unable to determine the correct value.";
                }
                identity EXTENDED_TERMINATION_DIRECTION {
                    description    
                "none";
                }
                identity EXTENDED_TERMINATION_DIRECTION_CONTRA_DIRECTION_SINK {
                    base EXTENDED_TERMINATION_DIRECTION;
                    description    
                "The essential flow of the Termination entity is SINK (i.e. up the layer stack) but the INPUT flow of the Termination entity was provided by a SOURCE OUTPUT or taken from a SOURCE INPUT (duplicating the input signal) hence reversing the flow orientation from down the layer stack to up the layer stack.";
                }
                identity EXTENDED_TERMINATION_DIRECTION_CONTRA_DIRECTION_SOURCE {
                    base EXTENDED_TERMINATION_DIRECTION;
                    description    
                "The essential flow of the Termination entity is SOURCE (i.e. down the layer stack) but the OUTPUT flow of the Termination entity was fed to (and replaces) a SINK OUTPUT or was fed to a SINK INPUT (replacing the normal flow) hence reversing the flow orientation from down the layer stack to up the layer stack.";
                }
                identity TERMINATION_STATE {
                    description    
                "none";
                }
                identity TERMINATION_STATE_LP_CAN_NEVER_TERMINATE {
                    base TERMINATION_STATE;
                    description    
                "A non-flexible case that can never be terminated.";
                }
                identity TERMINATION_STATE_LP_NOT_TERMINATED {
                    base TERMINATION_STATE;
                    description    
                "A flexible termination that can terminate but is currently not terminated.";
                }
                identity TERMINATION_STATE_TERMINATED_SERVER_TO_CLIENT_FLOW {
                    base TERMINATION_STATE;
                    description    
                "A flexible termination that is currently terminated for server to client flow only.";
                }
                identity TERMINATION_STATE_TERMINATED_CLIENT_TO_SERVER_FLOW {
                    base TERMINATION_STATE;
                    description    
                "A flexible termination that is currently terminated for client to server flow only.";
                }
                identity TERMINATION_STATE_TERMINATED_BIDIRECTIONAL {
                    base TERMINATION_STATE;
                    description    
                "A flexible termination that is currently terminated in both directions of flow.";
                }
                identity TERMINATION_STATE_LP_PERMENANTLY_TERMINATED {
                    base TERMINATION_STATE;
                    description    
                "A non-flexible termination that is always terminated (in both directions of flow for a bidirectional case and in the one direction of flow for both unidirectional cases).";
                }
                identity TERMINATION_STATE_TERMINATION_STATE_UNKNOWN {
                    base TERMINATION_STATE;
                    description    
                "There TerminationState cannot be determined.";
                }
                identity PROTECTION_REASON {
                    description    
                "none";
                }
                identity PROTECTION_REASON_WAIT_TO_REVERT {
                    base PROTECTION_REASON;
                    description    
                "The resource is selected as control is waiting to restore to a preferred resource.";
                }
                identity PROTECTION_REASON_SIGNAL_DEGRADE {
                    base PROTECTION_REASON;
                    description    
                "The resource is selected as the best preferred resource is in signal degrade.";
                }
                identity PROTECTION_REASON_SIGNAL_FAIL {
                    base PROTECTION_REASON;
                    description    
                "The resource is selected as the best preferred resource is in signal fail.";
                }
                identity ROUTE_SELECTION_CONTROL {
                    description    
                "none";
                }
                identity ROUTE_SELECTION_CONTROL_LOCK_OUT {
                    base ROUTE_SELECTION_CONTROL;
                    description    
                "The resource is configured to temporarily not be available for use in the protection scheme(s) it is part of.
                        This overrides all other protection control states including forced.
                        If the item is locked out, then it cannot be used under any circumstances.
                        Note: Only relevant when part of a protection scheme.
                        Note: if a protection process that has a relationship to the item (i.e. is one of the options the protection process may choose) is deactivated by being isFrozen = true) then the lockout request will be rejected. ";
                }
                identity ROUTE_SELECTION_REASON {
                    description    
                "none";
                }
                identity SWITCH_CONTROL {
                    description    
                "none";
                }
                identity SWITCH_CONTROL_NORMAL {
                    base SWITCH_CONTROL;
                    description    
                "No administrative control applied to the switch.";
                }
                identity SWITCH_CONTROL_MANUAL {
                    base SWITCH_CONTROL;
                    description    
                "Resource temporarily chosen by control configuration where the resource is not the preferred resource.
                        Preferred resource has highest priority.
                        Temporarily overrides reversion.
                        If this resource fails, it will switch to best available resource. 
                        If resource selected is shared and another FC requires the resource, then the selection control will change to Normal and switch to best available based upon normal rules.
                        Cannot manually switch a Forced switch, cannot remove a forced switch, cannot switch to a locked out item and will be rejected if the protection process is deactivated by being Freeze = true).
                        A manual switch/route that is selecting an FcPort, LTP, FC, Link or Route that is subsequently set to LOCK_OUT will have the manual removed (changed to NORMAL) and will switch away from the FcPort with LOCK_OUT to best available based upon normal rules.
                        A manual switch that is selecting an FcPort that is subsequently selected by a Forced switch will be restored to normal operation and the manual will be removed.
                        A manual switch/route that is selecting an FcPort, LTP, FC, Link or Route that is subsequently manual selected by another switch/route will have the manual removed and will switch away from the FcPort.
                        Can be returned to NORMAL by configuration action.";
                }
                identity SWITCH_CONTROL_FORCED {
                    base SWITCH_CONTROL;
                    description    
                "Resource temporarily chosen by control configuration where the resource is not the preferred resource.
                        Preferred resource has highest priority.
                        Temporarily overrides reversion.
                        If this resource fails it will NOT switch. 
                        If resource selected is shared and another FC requires the resource through a FORCE on that FC and the FC is of a higher FcPriority then the selection control on this FC will change to NORMAL and switch to best available based upon normal rules.
                        If the resource selected is then set to LOCK_OUT then the selection control will change to NORMAL and switch to best available based upon normal rules.
                        Can be returned to NORMAL by configuration action.";
                }
                identity SWITCH_STATE_REASON {
                    description    
                "none";
                }
                identity REVERSION_MODE {
                    description    
                "none";
                }
                identity REVERSION_MODE_REVERTIVE {
                    base REVERSION_MODE;
                    description    
                "An FC switched to a lower priority (non-preferred) resource will revert to a higher priority (preferred) resource when that recovers (potentially after some hold-off time).";
                }
                identity REVERSION_MODE_NON-REVERTIVE {
                    base REVERSION_MODE;
                    description    
                "An FC switched to a lower priority (non-preferred) resource will not revert to a higher priority (preferred) resource when that recovers.";
                }
                identity RESILIENCE_CONTROL {
                    description    
                "none";
                }
                identity RESILIENCE_CONTROL_QUIESCENT {
                    base RESILIENCE_CONTROL;
                    description    
                "none";
                }
                identity RESILIENCE_CONTROL_RESTORING {
                    base RESILIENCE_CONTROL;
                    description    
                "none";
                }
                identity RESILIENCE_CONTROL_RECOVERY_FAILED {
                    base RESILIENCE_CONTROL;
                    description    
                "none";
                }
                identity RESILIENCE_CONTROL_UNKNOWN {
                    base RESILIENCE_CONTROL;
                    description    
                "none";
                }
                identity RUN_MODE {
                    description    
                "none";
                }
                identity RUN_MODE_FREE_RUN {
                    base RUN_MODE;
                    description    
                "The clock is not synchronized to another clock.";
                }
                identity RUN_MODE_LOCKED {
                    base RUN_MODE;
                    description    
                "The clock is synchronized to another clock.";
                }
                identity RUN_MODE_HOLD_OVER {
                    base RUN_MODE;
                    description    
                "The clock was previously synchronized to another clock but that timing input has been lost.
                        The clock is set to the last known synchronization.";
                }
                identity LAYER_PROTOCOL_NAME {
                    description    
                "none";
                }
                identity LAYER_PROTOCOL_NAME_PHOTONIC_MEDIA {
                    base LAYER_PROTOCOL_NAME;
                    description    
                "The characteristic information is that of a channel able to carry photons and of the photon source/sink.";
                }
                identity LAYER_PROTOCOL_NAME_OTU_AND_ODU {
                    base LAYER_PROTOCOL_NAME;
                    description    
                "The characteristic information is that of a channel able to carry ODU/OTU protocol (OTN) and of the ODU/OTU source/sink.";
                }
                identity LAYER_PROTOCOL_NAME_ETHERNET {
                    base LAYER_PROTOCOL_NAME;
                    description    
                "The characteristic information is that of a channel able to carry Ethernet protocol and of the Ethernet protocol source/sink.";
                }
                identity OPERATIONAL_STATE {
                    description    
                "none";
                }
                identity OPERATIONAL_STATE_DISABLED {
                    base OPERATIONAL_STATE;
                    description    
                "The resource is unable to meet the SLA of the user of the resource. 
                        If no (explicit) SLA is defined the resource is disabled if it is totally inoperable and unable to provide service to the user.";
                }
                identity OPERATIONAL_STATE_ENABLED {
                    base OPERATIONAL_STATE;
                    description    
                "The resource is partially or fully operable and available for use.";
                }
                identity ADMINISTRATIVE_STATE {
                    description    
                "none";
                }
                identity ADMINISTRATIVE_STATE_LOCKED {
                    base ADMINISTRATIVE_STATE;
                    description    
                "Users are administratively prohibited from making use of the resource.";
                }
                identity ADMINISTRATIVE_STATE_UNLOCKED {
                    base ADMINISTRATIVE_STATE;
                    description    
                "Users are allowed to use the resource.";
                }
                identity ADMINISTRATIVE_STATE_SHUTTING_DOWN {
                    base ADMINISTRATIVE_STATE;
                    description    
                "The entity is administratively restricted to existing instances of use only. There may be specific actions to remove existing uses. No new instances of use can be enabled.
                        The resource automatically transitions to “locked” when the last user quits. 
                        The administrative state is not visible in the client context. 
                        The lifecycle state “pending removal” should be used to indicate to the client that the provider intends to remove the resource.";
                }
                identity ADMINISTRATIVE_CONTROL {
                    description    
                "none";
                }
                identity ADMINISTRATIVE_CONTROL_UNLOCK {
                    base ADMINISTRATIVE_CONTROL;
                    description    
                "The intention is for the entity to become unlocked.
                        The entity may already be UNLOCKED.";
                }
                identity ADMINISTRATIVE_CONTROL_LOCK_PASSIVE {
                    base ADMINISTRATIVE_CONTROL;
                    description    
                "The intention is for the entity to become locked but no effort is expected to move to the Locked state (the state will be achieved once all users stop using the resource). 
                        The entity may be LOCKED.";
                }
                identity ADMINISTRATIVE_CONTROL_LOCK_ACTIVE {
                    base ADMINISTRATIVE_CONTROL;
                    description    
                "The intention is for the entity to become locked and it is expected that effort will be made to move to the Locked state (users will be actively removed). 
                        The entity may already be LOCKED.";
                }
                identity ADMINISTRATIVE_CONTROL_LOCK_IMMEDIATE {
                    base ADMINISTRATIVE_CONTROL;
                    description    
                "The intention is for the entity to become locked and it is expected to move to the Locked state immediately (users will be force removed). 
                        The entity may already be LOCKED.";
                }
                identity ADMINISTRATIVE_CONTROL_QUIESCENT {
                    base ADMINISTRATIVE_CONTROL;
                    description    
                "The administrative state is at a stable value (LOCKED/UNLOCKED) and no action is being taken.";
                }
                identity LIFECYCLE_STATE {
                    description    
                "none";
                }
                identity LIFECYCLE_STATE_PLANNED {
                    base LIFECYCLE_STATE;
                    description    
                "The resource is planned but is not present in the network.
                        Should include a 'time' when the resources are expected to be installed.";
                }
                identity LIFECYCLE_STATE_POTENTIAL_AVAILABLE {
                    base LIFECYCLE_STATE;
                    description    
                "The supporting resources are present in the network but are shared with other clients; or require further configuration before they can be used; or both.
                        (1) When a potential resource is configured and allocated to a client it is moved to the INSTALLED state for that client.
                        (2) If the potential resource has been consumed (e.g. allocated to another client) it is moved to the POTENTIAL BUSY state for all other clients.";
                }
                identity LIFECYCLE_STATE_POTENTIAL_BUSY {
                    base LIFECYCLE_STATE;
                    description    
                "The supporting resources are present in the network but have been allocated to other clients.";
                }
                identity LIFECYCLE_STATE_INSTALLED {
                    base LIFECYCLE_STATE;
                    description    
                "The resource is present in the network and is capable of providing the service.";
                }
                identity LIFECYCLE_STATE_PENDING_REMOVAL {
                    base LIFECYCLE_STATE;
                    description    
                "The resource has been marked for removal. Should include a “time” when the resources are expected to be removed.";
                }
                identity BLOCK_DIRECTION {
                    description    
                "none";
                }
                identity BLOCK_DIRECTION_NO_BLOCK {
                    base BLOCK_DIRECTION;
                    description    
                "The FC is not blocking signal related to the LTP.";
                }
                identity BLOCK_DIRECTION_INGRESS_BLOCK {
                    base BLOCK_DIRECTION;
                    description    
                "The FC is blocking signal that is flowing into the LTP from the FC.";
                }
                identity BLOCK_DIRECTION_EGRESS_BLOCK {
                    base BLOCK_DIRECTION;
                    description    
                "The FC is blocking signal flowing out of the LTP to the FC.";
                }
                identity BLOCK_DIRECTION_BIDIRECTIONAL_BLOCK {
                    base BLOCK_DIRECTION;
                    description    
                "The FC is blocking both directions of traffic, i.e. Ingress and Egress, to/from the LTP.";
                }
                identity CONNECTOR_AND_PIN_ORIENTATION {
                    description    
                "none";
                }
                identity CONNECTOR_AND_PIN_ORIENTATION_MALE {
                    base CONNECTOR_AND_PIN_ORIENTATION;
                    description    
                "The connecting elements are dominantly protrusions.";
                }
                identity CONNECTOR_AND_PIN_ORIENTATION_FEMALE {
                    base CONNECTOR_AND_PIN_ORIENTATION;
                    description    
                "The connecting elements are dominantly indentations.";
                }
                identity CONNECTOR_AND_PIN_ORIENTATION_SYMMETRIC_NEUTRAL {
                    base CONNECTOR_AND_PIN_ORIENTATION;
                    description    
                "The pin (and housing) orientation combination is such that it is symmetric so a connector is compatible with itself.
                        The connecting element may be a surface rather than protrusions or indentations.";
                }
                identity EQUIPMENT_CATEGORY {
                    description    
                "none";
                }
                identity EQUIPMENT_CATEGORY_SUBRACK {
                    base EQUIPMENT_CATEGORY;
                    description    
                "An assembly with holders designed to accommodate CIRCUIT_PACKs. 
                        The assembly is designed to be mounted in a RACK.";
                }
                identity EQUIPMENT_CATEGORY_CIRCUIT_PACK {
                    base EQUIPMENT_CATEGORY;
                    description    
                "An assembly with connectors compatible with those in a holder.
                        The assembly is designed to be mounted in a holder (SLOT) of a SUBRACK.
                        May also support holders (SLOTs) for SMALL_FORMFACTOR_PLUGGABLEs.";
                }
                identity EQUIPMENT_CATEGORY_SMALL_FORMFACTOR_PLUGGABLE {
                    base EQUIPMENT_CATEGORY;
                    description    
                "A small assembly (compared to a CIRCUIT_PACK) with connectors compatible with those in a holder.
                        The assembly is designed to be mounted in a holder (SLOT) of a CIRCUIT_PACK or STAND_ALONE_UNIT.";
                }
                identity EQUIPMENT_CATEGORY_STAND_ALONE_UNIT {
                    base EQUIPMENT_CATEGORY;
                    description    
                "An assembly with connectors for cabling and potentially with holders.
                        The assembly is designed to be mounted in a freeform environment (on a table or simple mechanical cabinet).
                        May support holders (SLOTs) for CIRCUIT_PACKs or for SMALL_FORMFACTOR_PLUGGABLEs.";
                }
                identity EQUIPMENT_CATEGORY_RACK {
                    base EQUIPMENT_CATEGORY;
                    description    
                "A mechanical assembly with cabling and predefined mounting points for particular SUBRACK types.
                        The assembly is designed to be mounted on the floor in a row with other RACKs.";
                }
                identity HOLDER_CATEGORY {
                    description    
                "none";
                }
                identity HOLDER_CATEGORY_SLOT {
                    base HOLDER_CATEGORY;
                    description    
                "A guided holder with fixed connectors.
                        The guided holder is designed to take a particular form of CIRCUIT_PACK or SMALL_FORMFACTOR_PLUGGABLE";
                }
                identity FORWARDING_RULE {
                    description    
                "none";
                }
                identity FORWARDING_RULE_CANNOT_FORWARD_ACROSS_FD_LINK {
                    base FORWARDING_RULE;
                    description    
                "LTPs referenced by the FD (or indirectly by the Link between FDs) cannot have FCs created between them.
                        This rule overrides all others.";
                }
                identity FORWARDING_RULE_MUST_FORWARD_ACROSS_FD_LINK {
                    base FORWARDING_RULE;
                    description    
                "LTPs referenced by the FD (or indirectly by the Link between FDs) MUST have FCs created between them.
                        This rule overrides all others except the CANNOT_FORWARD rule.";
                }
                identity FORWARDING_RULE_MAY_FORWARD_ACROSS_FD_LINK {
                    base FORWARDING_RULE;
                    description    
                "LTPs referenced by the FD (or indirectly by the Link between FDs) may have FCs created between them.
                        FCs may not be created between points that are not related by this rule either directly in an FD or indirectly via a Link linking two or more FDs.
                        For a Link points in an FD at one end of the Link can be connected to points in an FD at an other end of the Link.";
                }
                identity FORWARDING_RULE_NULL_FORWARDING_RULE {
                    base FORWARDING_RULE;
                    description    
                "none";
                }
                identity RULE_TYPE {
                    description    
                "none";
                }
                identity RULE_TYPE_FORWARDING {
                    base RULE_TYPE;
                    description    
                "The rule relates to creation of FCs.";
                }
                identity RULE_TYPE_COST {
                    base RULE_TYPE;
                    description    
                "The rule relates to forwarding cost.";
                }
                identity RULE_TYPE_RISK {
                    base RULE_TYPE;
                    description    
                "The rule relates to forwarding risk.";
                }
                identity RULE_TYPE_CAPACITY {
                    base RULE_TYPE;
                    description    
                "none";
                }
                identity PORT_ROLE_RULE_OPTION {
                    description    
                "none";
                }
                identity PORT_ROLE_RULE_OPTION_SAME_ROLE {
                    base PORT_ROLE_RULE_OPTION;
                    description    
                "The ports to which the rule applies must have role from the list in PortRole.";
                }
                identity PORT_ROLE_RULE_OPTION_DIFFERENT_ROLE {
                    base PORT_ROLE_RULE_OPTION;
                    description    
                "The ports to which the rule applies must not have a role from the list in PortRole.";
                }
                identity PORT_ROLE_RULE_OPTION_ANY_ROLE {
                    base PORT_ROLE_RULE_OPTION;
                    description    
                "The rule applies to any role of port.";
                }
                identity SIGNAL_PROPERTY_VALUE_RULE {
                    description    
                "none";
                }
                identity SIGNAL_PROPERTY_VALUE_RULE_SAME_VALUE {
                    base SIGNAL_PROPERTY_VALUE_RULE;
                    description    
                "none";
                }
                identity SIGNAL_PROPERTY_VALUE_RULE_ANY_VALUE {
                    base SIGNAL_PROPERTY_VALUE_RULE;
                    description    
                "none";
                }
                identity PARTNER {
                    description    
                "none";
                }
                identity PARTNER_FC {
                    base PARTNER;
                    description    
                "ForwardingConstruct.";
                }
                identity PARTNER_FD {
                    base PARTNER;
                    description    
                "ForwardingDomain.";
                }
                identity PARTNER_LINK {
                    base PARTNER;
                    description    
                "Link.";
                }
                identity PARTNER_CASC {
                    base PARTNER;
                    description    
                "ConfigurationAndSwitchController.";
                }
                identity PARTNER_CC {
                    base PARTNER;
                    description    
                "ControlConstruct.";
                }
                identity PARTNER_CD {
                    base PARTNER;
                    description    
                "ConstraintDomain.";
                }
                identity PARTNER_PC {
                    base PARTNER;
                    description    
                "ProcessingConstruct.";
                }
                identity PARTNER_PEER {
                    base PARTNER;
                    description    
                "LTP peer.";
                }
                identity PARTNER_CLIENT {
                    base PARTNER;
                    description    
                "LTP client.";
                }
                identity PARTNER_SERVER {
                    base PARTNER;
                    description    
                "LTP server.";
                }
                identity PARTNER_VIEW {
                    base PARTNER;
                    description    
                "LTP in other view.";
                }
                identity TASK_LIFECYCLE_STATE {
                    description    
                "none";
                }
                identity TASK_LIFECYCLE_STATE_RUNNING {
                    base TASK_LIFECYCLE_STATE;
                    description    
                "The task is running.";
                }
                identity TASK_LIFECYCLE_STATE_PAUSED {
                    base TASK_LIFECYCLE_STATE;
                    description    
                "The task has been paused.";
                }
                identity TASK_LIFECYCLE_STATE_WAITING {
                    base TASK_LIFECYCLE_STATE;
                    description    
                "The task is waiting for input etc.";
                }
                identity TASK_LIFECYCLE_STATE_ABORTING {
                    base TASK_LIFECYCLE_STATE;
                    description    
                "The task is aborting.";
                }
                identity TASK_LIFECYCLE_STATE_COMPLETED {
                    base TASK_LIFECYCLE_STATE;
                    description    
                "The task has been completed successfully.";
                }
                identity TASK_LIFECYCLE_STATE_ABORTED {
                    base TASK_LIFECYCLE_STATE;
                    description    
                "The task has been aborted.";
                }
                identity TASK_LIFECYCLE_STATE_ATTEMPTING_ROLLBACK {
                    base TASK_LIFECYCLE_STATE;
                    description    
                "The task is attempting to return the controlled system to a previous state.";
                }
                identity TASK_LIFECYCLE_STATE_ROLLBACK_COMPLETE {
                    base TASK_LIFECYCLE_STATE;
                    description    
                "The task has completed a roll back action.";
                }
                identity TASK_LIFECYCLE_STATE_ABANDONING {
                    base TASK_LIFECYCLE_STATE;
                    description    
                "Task is abandoning.";
                }
                identity TASK_LIFECYCLE_STATE_ABANDONED {
                    base TASK_LIFECYCLE_STATE;
                    description    
                "The task has been abandoned and is no longer running.";
                }
                identity TASK_LIFECYCLE_STATE_FAILED {
                    base TASK_LIFECYCLE_STATE;
                    description    
                "The task has failed.";
                }
                identity TASK_LIFECYCLE_STATE_ARCHIVED {
                    base TASK_LIFECYCLE_STATE;
                    description    
                "The task has been archived (and is no longer running).";
                }
                identity PROGRESS_STATUS {
                    description    
                "none";
                }
                identity PROGRESS_STATUS_COMPLETE {
                    base PROGRESS_STATUS;
                    description    
                "none";
                }
                identity PROGRESS_STATUS_IN_PROGRESS {
                    base PROGRESS_STATUS;
                    description    
                "none";
                }
                identity PROGRESS_STATUS_FAILED {
                    base PROGRESS_STATUS;
                    description    
                "none";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity.";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity.";
                }
                identity TERMINATION_DIRECTION_UNDEFINED_OR_UNKNOWN {
                    base TERMINATION_DIRECTION;
                    description    
                "Not a normal state. The system is unable to determine the correct value.";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base TERMINATION_DIRECTION;
                    description    
                "Not a normal state. The system is unable to determine the correct value.";
                }
                identity ACTION_VERBS {
                    description    
                "none";
                }
                identity ACTION_VERBS_CREATE_POST_ADD {
                    base ACTION_VERBS;
                    description    
                "none";
                }
                identity ACTION_VERBS_SET_UPDATE_PUT_MODIFY_WRITE_ADD {
                    base ACTION_VERBS;
                    description    
                "none";
                }
                identity ACTION_VERBS_GET_READ {
                    base ACTION_VERBS;
                    description    
                "none";
                }
                identity ACTION_VERBS_DELETE_REMOVE {
                    base ACTION_VERBS;
                    description    
                "none";
                }
                identity DIRECTION {
                    description    
                "none";
                }
                identity DIRECTION_IN {
                    base DIRECTION;
                    description    
                "none";
                }
                identity DIRECTION_OUT {
                    base DIRECTION;
                    description    
                "none";
                }
                identity DIRECTION_BIDIRECTIONAL {
                    base DIRECTION;
                    description    
                "none";
                }
                identity ACTION_VERBS {
                    description    
                "none";
                }
                identity ACTION_VERBS_CREATE_POST_ADD {
                    base ACTION_VERBS;
                    description    
                "Cause the addition of some structure.";
                }
                identity ACTION_VERBS_SET_UPDATE_PUT_MODIFY_WRITE_ADD {
                    base ACTION_VERBS;
                    description    
                "Cause the adjustment to some properties.";
                }
                identity ACTION_VERBS_GET_READ {
                    base ACTION_VERBS;
                    description    
                "Acquire information.";
                }
                identity ACTION_VERBS_DELETE_REMOVE {
                    base ACTION_VERBS;
                    description    
                "Eliminate some structure.";
                }
                identity ACTIVITY_DIRECTIVE {
                    description    
                "none";
                }
                identity ACTIVITY_DIRECTIVE_STRUCTURE_IS_NOT {
                    base ACTIVITY_DIRECTIVE;
                    description    
                "The structure defined should not be present. No part should be present (within the stated degrees of precision.";
                }
                identity ACTIVITY_DIRECTIVE_NEW_STRUCTURE_AND_VALUES {
                    base ACTIVITY_DIRECTIVE;
                    description    
                "None of the structure stated is expected to be present, but is required.";
                }
                identity ACTIVITY_DIRECTIVE_INCREMENTAL_STRUCTURE_AND_VALUES {
                    base ACTIVITY_DIRECTIVE;
                    description    
                "The structure stated is an increment on what already exists.
                        Increment in this case may also be decrement.";
                }
                identity ACTIVITY_DIRECTIVE_ONLY_VALUES_IN_EXISTING_STRUCTURE {
                    base ACTIVITY_DIRECTIVE;
                    description    
                "Only values should be modified, no new structure should be created and no structure should be deleted.";
                }
                identity ACTIVITY_DIRECTIVE_DEFINED_BY_VERB {
                    base ACTIVITY_DIRECTIVE;
                    description    
                "A verb is provided to give guidance (such as Create).";
                }
                identity ACTION_EFFORT {
                    description    
                "none";
                }
                identity ACTION_EFFORT_BEST_EFFORT {
                    base ACTION_EFFORT;
                    description    
                "none";
                }
                identity ACTION_EFFORT_EXACT_MATCH {
                    base ACTION_EFFORT;
                    description    
                "none";
                }
                identity PAUSE_RESUME_RULE {
                    description    
                "none";
                }
                identity PAUSE_RESUME_RULE_NO_PAUSE_POSSIBLE {
                    base PAUSE_RESUME_RULE;
                    description    
                "none";
                }

            /****************************************
            * grouping statements for object classes
            **************************************/ 
                grouping network-scheme-specification {
                    leaf scheme-name {
                        type string;
                        description    
                    "none";
                    }
                    leaf external-definition-of-scheme {
                        type string;
                        description    
                    "none";
                    }
                    description    
                "none";
                }
                grouping profile-proxy {
                    leaf profile-proxy-mode {
                        type string;
                        description    
                    "A parameter profile may be used in a number of different ways:
                            - Forces the values on the target with no opportunity to see or override the values in the target
                            - Sets the values on the target that can be seen on the target
                            - Sets the values on the target and supports override on the target so the target can be set away from the value in the profile
                            - etc.";
                    }
                    container control-parameters {
                        uses control-parameters-pac;
                        description    
                "The control parameters that can be set int the profile and applied to the target.
                            Not all parameters need be selected and applied.";
                    }
                    description    
                "A lightweight sketch placeholder for the profile model.";
                }


        /****************************************
        * package modeling-enhancements
        **************************************/ 
            /****************************************
            * package rules
            **************************************/ 

            /****************************************
            * package view-abstraction-rule-sketch
            **************************************/ 
                grouping view-abstraction-rules {
                    leaf-list -ltp-relatest-to-ltp-in-other-view {
                        type string;
                        description     
                 "none";
                    }
                    description    
                "Provides rules and access to policies that govern and explain the view abstraction.
                        At this point it appears that this is not necessary however it has been left in the model as there is still some view abstraction work to be done.";
                }

            /****************************************
            * package lifecycle-dependency
            **************************************/ 
                grouping lifecycle-scoping-class {
                    list composed-dependent {
                        uses dependent-class;
                        description    
                "none";
                    }
                    description    
                "none";
                }
                grouping dependent-class {
                    container lifecycle-scoping-class {
                        uses lifecycle-scoping-class;
                        description    
                "none";
                    }
                    container related-lifecycle-scoping-class {
                        uses lifecycle-scoping-class;
                        description    
                "none";
                    }
                    description    
                "none";
                }


        /****************************************
        * package inter-view-relationships-sketch
        **************************************/ 
            grouping sketch-fc {
                leaf supporting-fc-in-other-view {
                    type leafref {
                        pathmust "/core-model:sketch-fc/core-model:";
                    require-instance false;
                    }
                must  'deref(.) = current()';
                    description    
                    "none";
                }
                leaf-list suported-fc-in-other-view {
                    type leafref {
                        pathmust "/core-model:sketch-fc/core-model:";
                    require-instance false;
                    }
                must  'deref(.) = current()';
                    description     
                 "none";
                }
                description    
                "none";
            }
            grouping sketch-ltp {
                leaf supporting-ltp-in-other-view {
                    type leafref {
                        pathmust "/core-model:sketch-ltp/core-model:";
                    require-instance false;
                    }
                must  'deref(.) = current()';
                    description    
                    "none";
                }
                leaf-list supported-ltp-in-other-view {
                    type leafref {
                        pathmust "/core-model:sketch-ltp/core-model:";
                    require-instance false;
                    }
                must  'deref(.) = current()';
                    description     
                 "none";
                }
                description    
                "none";
            }

        /****************************************
        * package enhancements-for-media
        **************************************/ 


    /****************************************
    * package explanatory-figures-used-in-documents-and-slides
    **************************************/ 

    /****************************************
    * package core-physical-model
    **************************************/ 
        /****************************************
        * package rule-models
        **************************************/ 
            /****************************************
            * package fru-non-fru-rules
            **************************************/ 
                /****************************************
                * grouping statements for object classes
                **************************************/ 
                    grouping field-replaceable {
                        list equipment-non-fru {
                            uses non-field-replaceable;
                            description    
                "none";
                        }
                        list holder {
                            uses holder;
                            description    
                "none";
                        }
                        container holder-address {
                            uses holder;
                            description    
                "none";
                        }
                        list connector {
                            uses connector;
                            description    
                "none";
                        }
                        uses equipment;
                        description    
                "A rule class (an abstract specialization of Equipment) that represents an equipment that can be replaced in the field. 
                            May plug in to a holder in another equipment (if not stand-alone). 
                            Realization could use an FRU Boolean on Equipment.";
                    }
                    grouping non-field-replaceable {
                        uses equipment;
                        description    
                "A rule class (an abstract specialization of Equipment) that represents an equipment that cannot be replaced in the field.
                            Is simply a subordinate part of an FRU (or another NFRU – where there must be an FRU at the top of the hierarchy). 
                            Does not have any exposed holders (any associated holders are assumed to belong to the containing FRU).
                            Does not have any connectors (any associated connectors are assumed to belong to the containing FRU).
                            ";
                    }


            /****************************************
            * package connector-rules
            **************************************/ 
                /****************************************
                * grouping statements for object classes
                **************************************/ 
                    grouping connector-in-holder {
                        container connector-on-equipment-for-holder {
                            uses connector-on-equipment-for-holder;
                            description    
                "The holder connector has a connector from the referenced equipment plugged into it.";
                        }
                        uses connector;
                        description    
                "A rule class (an abstract specialization of Connector) that represents a connector that are only accessible to an equipment inserted in the holder.";
                    }
                    grouping connector-cable-end {
                        container connector-on-equipment-for-cable {
                            uses connector-on-equipment-for-cable;
                            description    
                "The cable connector is plugged into a connector on an Equipment.";
                        }
                        leaf connector-on-cable-end {
                            type string;
                            description    
                    "The cable is joined to another cable via connectors.";
                        }
                        uses connector;
                        description    
                "A rule class (an abstract specialization of Connector) that represents a connector on the end of a cable.";
                    }
                    grouping connector-on-equipment-for-cable {
                        container connector-cable-end {
                            uses connector-cable-end;
                            description    
                "The connector on an equipment has a cable plugged into it.";
                        }
                        uses connector;
                        description    
                "A rule class (an abstract specialization of Connector) that represents a connector exposed on an equipment such that a cable may be plugged in.";
                    }
                    grouping connector-on-equipment-for-holder {
                        container connector-in-holder {
                            uses connector-in-holder;
                            description    
                "The equipment connector is plugged into the referenced holder connector.";
                        }
                        uses connector;
                        description    
                "A rule class (an abstract specialization of Connector) that represents a connector on an equipment that is intended to mate with a connector in a holder.";
                    }



        /****************************************
        * package equipment-detail
        **************************************/ 
            /****************************************
            * grouping statements for object classes
            **************************************/ 
                /****************************************
                * package dynamic-details
                **************************************/ 
                    grouping function-enablers {
                        leaf power-state {
                            type to-be-defined;
                            description    
                    "The state of the power being supplied to the equipment.
                                Note that this attribute summarizes the power state. 
                                Full details on the actual power system would be provided from a number of PC instances representing the relevant parts of the Power function (e.g. different voltage supplies).";
                        }
                        description    
                "Represents the dynamic aspects of the properties that relate to the motive force that directly enable functionality to emerge from the equipment.";
                    }
                    grouping mechanical-functions {
                        leaf rotation-speed {
                            type to-be-defined;
                            description    
                    "none";
                        }
                        description    
                "Represents the dynamic aspects of the mechanical functions of the equipment.";
                    }
                    grouping physical-properties {
                        leaf temperature {
                            type to-be-defined;
                            description    
                    "none";
                        }
                        description    
                "Represents the dynamic aspects of the physical environmental properties of the equipment.";
                    }
                    grouping holder-monitor {
                        leaf is-active {
                            type boolean;
                            description    
                    "Indicates that the holder is active and is supporting an Equipment instance.";
                        }
                        leaf is-actual-mismatch-with-expected {
                            type boolean;
                            description    
                    "Indicates that the equipment in the holder does not match the equipment expected to be in the holder.";
                        }
                        container aggregate-function {
                            uses aggregate-function;
                            description    
                "Obsolete";
                        }
                        container supporting-pc {
                            uses processing-construct;
                            description    
                "The functionality supporting this entity.";
                        }
                        description    
                "Represents the dynamic state of the holder instance. ";
                    }
                    grouping location {
                        container equipment-location {
                            uses address;
                            description    
                "none";
                        }
                        container geographical-location {
                            uses address;
                            description    
                "none";
                        }
                        description    
                "Represents where the equipment is.";
                    }

                /****************************************
                * package invariant-details
                **************************************/ 
                    grouping equipment-structure {
                        leaf category {
                            type equipment-category;
                            description    
                    "This attribute provides the identifier for a category of equipments regarded as having particular shared characteristics.";
                        }
                        description    
                "Represents the form of the equipment.";
                    }
                    grouping equipment-instance {
                        leaf manufacture-date {
                            type string;
                            description    
                    "This attribute represents the date on which this instance is manufactured.";
                        }
                        leaf serial-number {
                            type string;
                            description    
                    "This attribute represents the serial number of this instance.";
                        }
                        leaf asset-instance-identifier {
                            type string;
                            description    
                    "This attribute represents the asset identifier of this instance from the manufacturer's perspective.";
                        }
                        description    
                "Represents the per instance invariant properties of the equipment.";
                    }
                    grouping equipment-type {
                        leaf description {
                            type string;
                            description    
                    "Text describing the type of Equipment.";
                        }
                        leaf model-identifier {
                            type string;
                            description    
                    "This attribute identifies the model of the equipment.";
                        }
                        leaf part-type-identifier {
                            type string;
                            description    
                    "This attribute identifies the part type of the equipment.";
                        }
                        leaf type-name {
                            type string;
                            description    
                    "This attribute identifies the type of the equipment.";
                        }
                        leaf version {
                            type string;
                            description    
                    "This attribute identifies the version of the equipment.";
                        }
                        description    
                "Represents the invariant properties of the equipment that define and characterize the type.";
                    }
                    grouping holder-structure {
                        leaf holder-category {
                            type holder-category;
                            description    
                    "none";
                        }
                        leaf is-captive {
                            type boolean;
                            description    
                    "none";
                        }
                        leaf is-guided {
                            type boolean;
                            description    
                    "This attribute indicates whether the holder has guides that constrain the position of the equipment in the holder or not.";
                        }
                        leaf is-quantised-space {
                            type boolean;
                            description    
                    "none";
                        }
                        description    
                "Represents the form of the holder.";
                    }
                    grouping manufactured-thing {
                        container manufacturer-properties {
                            uses manufacturer-properties;
                            description    
                "none";
                        }
                        container equipment-type {
                            uses equipment-type;
                            description    
                "none";
                        }
                        container equipment-instance {
                            uses equipment-instance;
                            description    
                "none";
                        }
                        container operator-augmented-equipment-type {
                            uses operator-augmented-equipment-type;
                            description    
                "none";
                        }
                        container operator-augmented-equipment-instance {
                            uses operator-augmented-equipment-instance;
                            description    
                "none";
                        }
                        description    
                "Collects all invariant aspects of a manufactured thing.";
                    }
                    grouping manufacturer-properties {
                        leaf manufacturer-identifier {
                            type string;
                            description    
                    "none";
                        }
                        leaf manufacturer-name {
                            type string;
                            description    
                    "none";
                        }
                        description    
                "Represents the properties of the manufacturer.";
                    }
                    grouping mechanical-features {
                        description    
                "Represents the invariant characteristics of dynamic mechanical features of a physical thing.";
                    }
                    grouping operator-augmented-equipment-type {
                        leaf asset-type-identifier {
                            type string;
                            description    
                    "none";
                        }
                        description    
                "Represents the invariant properties of the equipment asset allocated by the operator that define and characterize the type.";
                    }
                    grouping physical-characteristics {
                        leaf weight-characeristics {
                            type to-be-defined;
                            description    
                    "none";
                        }
                        leaf fire-characteristics {
                            type to-be-defined;
                            description    
                    "none";
                        }
                        leaf materials {
                            type to-be-defined;
                            description    
                    "none";
                        }
                        description    
                "Represents the invariant physical characteristics (including composition and physical robustness) of the type.";
                    }
                    grouping environmental-rating {
                        container thermal-rating {
                            uses thermal-rating;
                            description    
                "This attribute represents the thermal characteristics (preferred maximum/minimum, absolute maximum/minimum etc) that the entity can tolerate.";
                        }
                        container power-rating {
                            uses power-rating;
                            description    
                "This attribute represents the power chracteristics (peak and mean per power source) of the entity.
                                For an Equipment this is the power consumption.
                                For a Holder this is the power that can be conveyed.";
                        }
                        leaf humidity-rating {
                            type to-be-defined;
                            description    
                    "This attribute represents the humidity characteristics (preferred maximum/minimum, absolute maximum/minimum etc.) that the entity can tolerate.";
                        }
                        description    
                "Represents the invariant physical operational boundaries for the equipment/holder type.";
                    }
                    grouping position {
                        leaf relative-position {
                            type to-be-defined;
                            description    
                    "none";
                        }
                        description    
                "Represents the invariant relative position of the holder (with respect to some frame of reference in an equipment) or connector on an equipment or pin in a connector.";
                    }
                    grouping spatial-properties-of-type {
                        leaf height {
                            type to-be-defined;
                            description    
                    "none";
                        }
                        leaf width {
                            type to-be-defined;
                            description    
                    "none";
                        }
                        leaf length {
                            type to-be-defined;
                            description    
                    "none";
                        }
                        description    
                "Represents the basic invariant spatial properties of a physical thing.";
                    }
                    grouping swappability {
                        leaf is-hot-swappable {
                            type boolean;
                            default "true";
                            description    
                    "none";
                        }
                        description    
                "Represents the degree of field replacement that is possible for the equipment type.";
                    }
                    grouping operator-augmented-equipment-instance {
                        leaf asset-instance-identifier {
                            type string;
                            description    
                    "This attribute represents the asset identifier of this instance from the operator's perspective.";
                        }
                        description    
                "Represents the invariant properties of the equipment asset allocated by the operator that define and characterize the type.";
                    }

                /****************************************
                * package pattern-classes
                **************************************/ 
                    grouping cable-details {
                        container spatial-properties-of-type {
                            uses spatial-properties-of-type;
                            description    
                "none";
                        }
                        container physical-characteristics {
                            uses physical-characteristics;
                            description    
                "none";
                        }
                        container manufactured-thing {
                            uses manufactured-thing;
                            description    
                "none";
                        }
                        description    
                "none";
                    }
                    grouping connector-details {
                        container position {
                            uses position;
                            description    
                "none";
                        }
                        container mechanical-features {
                            uses mechanical-features;
                            description    
                "none";
                        }
                        container manufactured-thing {
                            uses manufactured-thing;
                            description    
                "none";
                        }
                        description    
                "none";
                    }
                    grouping equipment-detail {
                        container location {
                            uses location;
                            description    
                "none";
                        }
                        container structure {
                            uses equipment-structure;
                            description    
                "none";
                        }
                        container swappability {
                            uses swappability;
                            description    
                "none";
                        }
                        container physical-properties {
                            uses physical-properties;
                            description    
                "none";
                        }
                        container function-enablers {
                            uses function-enablers;
                            description    
                "none";
                        }
                        container mechanical-functions {
                            uses mechanical-functions;
                            description    
                "none";
                        }
                        container physical-characteristics {
                            uses physical-characteristics;
                            description    
                "none";
                        }
                        container mechanical-features {
                            uses mechanical-features;
                            description    
                "none";
                        }
                        container spatial-properties-of-type {
                            uses spatial-properties-of-type;
                            description    
                "none";
                        }
                        container environmental-rating {
                            uses environmental-rating;
                            description    
                "none";
                        }
                        container manufactured-thing {
                            uses manufactured-thing;
                            description    
                "none";
                        }
                        uses local-class;
                        description    
                "none";
                    }
                    grouping holder-details {
                        container spatial-properties-of-type {
                            uses spatial-properties-of-type;
                            description    
                "none";
                        }
                        container environmental-rating {
                            uses environmental-rating;
                            description    
                "none";
                        }
                        list holder-monitor {
                            uses holder-monitor;
                            description    
                "none";
                        }
                        container position {
                            uses position;
                            description    
                "none";
                        }
                        container holder-structure {
                            uses holder-structure;
                            description    
                "none";
                        }
                        uses local-class;
                        description    
                "none";
                    }


            /****************************************
            * package data-types
            **************************************/ 
                grouping thermal-rating {
                    leaf thermal-rating-name {
                        type string;
                        description    
                    "Name of the rating property, e.g. Absolute.";
                    }
                    leaf maximum-temperature {
                        type decimal64{ fraction-digits 3; }
                        description    
                    "The maximum temperature in Celsius.";
                    }
                    leaf minimum-temperature {
                        type decimal64{ fraction-digits 3; }
                        description    
                    "The minimum temperature in Celsius.";
                    }
                    description    
                "A thermal rating value range.";
                }
                grouping power-rating {
                    leaf power-rating-name {
                        type string;
                        description    
                    "Name of the rating property, e.g. Absolute.";
                    }
                    leaf power-rating-value {
                        type string;
                        description    
                    "none";
                    }
                    description    
                "none";
                }


        /****************************************
        * package equipment-pattern-structure
        **************************************/ 
            /****************************************
            * grouping statements for object classes
            **************************************/ 
                grouping cable {
                    list connector {
                        uses connector;
                        description    
                "A connector that terminates the Cable to support the cable and/or allow signal flow into/out of the Cable.";
                    }
                    container mechanical-features {
                        uses mechanical-features;
                        description    
                "none";
                    }
                    list strand {
                        uses strand;
                        description    
                "none";
                    }
                    leaf-list bundled-cable {
                        type leafref {
                            pathmust "/core-model:cable/core-model:bundled-cable/core-model:";
                    require-instance false;
                        }
                must  'deref(.) = current()';
                        description     
                 "none";
                    }
                    uses global-class;
                    uses group-of-strands;
                    description    
                "Basic model representing a cable with connectors fitted at the cable ends as appropriate.
                        The cable may be an abstraction where the apparent ends are actually ends of two different cables that are connected indirectly by other cables and where that cable detail is not relevant or is not known.
                        This is intentionally a very basic representation of a cable. 
                        The model does not account for any outside plant considerations.
                        In a more sophisticated representation cable ends might be represented that then associate to the attached connector. 
                        At this point it is assumed that the basic model is sufficient.";
                }
                grouping connector {
                    leaf connector {
                        type string;
                        description    
                    "The Connector that is attached to this Connector so as to join the Equipment/Cable with this Connector to another Equipment/Cable.
                            This may provide physical support and/or allow signal flow.";
                    }
                    list pin {
                        min-elements 1;
                        uses pin;
                        description    
                "none";
                    }
                    leaf orientation {
                        type connector-and-pin-orientation;
                        description    
                    "The physical orientation of the connector, such as whether it is a male, or female, or neutral structure.";
                    }
                    container pin-layout {
                        uses pin-layout;
                        description    
                "none";
                    }
                    leaf connector-type {
                        type to-be-defined;
                        description    
                    "The type of the connector.";
                    }
                    leaf role {
                        type string;
                        description    
                    "The purpose of the Connector in the physical space and the functional space.";
                    }
                    uses local-class;
                    uses pin-group;
                    description    
                "Represents a connector that may be fully exposed (e.g. to plug in a cable or on the end of a cable) or partially exposed (e.g. backplane to plug in another piece of equipment such as a module).
                        A physical port on the Equipment. A place where signals produced by the functionality of the Equipment may be accessed.";
                }
                grouping equipment {
                    list connector {
                        uses connector;
                        description    
                "A Connector on the Equipment.";
                    }
                    list contained-holder {
                        uses holder;
                        description    
                "References the Holder in an Equipment that is available to take other Equipments.
                            For example:
                            - Slot in a sub-rack
                            - Slot in a Field Replaceable Unit that can take a small form-factor pluggable.";
                    }
                    container addressed-by-holder {
                        uses holder;
                        description    
                "A Holder through which the Equipment can be identified (where the Holder name/identifier is part of the Address).";
                    }
                    leaf-list encapsulated-non-fru {
                        type leafref {
                            pathmust "/core-model:equipment/core-model:encapsulated-non-fru/core-model:";
                    require-instance false;
                        }
                must  'deref(.) = current()';
                        description     
                 "An Equipment that is part of this Equipment and that is not separately field replaceable (i.e. will be field replaced with this Equipment).";
                    }
                    list exposed-cable {
                        uses cable;
                        description    
                "A Cable that is attached to part of the Equipment at one end and exposed at the other end through a Connector.";
                    }
                    list non-fru-support-position {
                        uses non-fru-support-position;
                        description    
                "none";
                    }
                    leaf is-field-replaceable {
                        type boolean;
                        default "true";
                        config false;
                        description    
                    "Indicates whether or not the equipment can be removed and replaced 'in the field' (i.e. in a deployment) by normal operations personnel.";
                    }
                    list function-block {
                        uses function-block;
                        description    
                "none";
                    }
                    list expected-equipment {
                        uses expected-equipment;
                        description    
                "none";
                    }
                    container actual-equipment {
                        uses actual-equipment;
                        description    
                "none";
                    }
                    container equipment-functional-boundary {
                        uses constraint-domain;
                        description    
                "none";
                    }
                    uses global-class;
                    description    
                "Represents any relevant physical thing. 
                        Can be either field replaceable or not field replaceable.
                        Note: The model is currently constrained to inside plant.";
                }
                grouping holder {
                    leaf-list connector {
                        type leafref {
                            pathmust "/core-model:field-replaceable/core-model:connector/core-model:";
                    require-instance false;
                        }
                must  'deref(.) = current()';
                        description     
                 "The connector associated with a Holder of an Equipment.
                            May represent connector on a backplane that takes Field Replaceable Units or a connector on a circuit pack that takes an SFP (Small Form-factor Pluggable).";
                    }
                    leaf occupying-fru {
                        type leafref {
                            pathmust "/core-model:equipment/core-model:encapsulated-non-fru/core-model:";
                    require-instance false;
                        }
                must  'deref(.) = current()';
                        description    
                    "The FRU that is occupying the holder. 
                            A holder may be unoccupied in reality, but always an abstract equipment object exists.
                            An FRU may occupy more hat one holder (using or blocking are intentionally not distinguished here).";
                    }
                    container holder-location {
                        uses address;
                        description    
                "The relative position of the holder in the context of its containing equipment along with the position of that containing Equipment (and further recursion).";
                    }
                    list supported-equipment-type {
                        min-elements 1;
                        uses supported-equipment-type;
                        description    
                "An Equipment type that the Holder can accommodate (is compatible with).";
                    }
                    container expected-holder {
                        uses expected-holder;
                        description    
                "none";
                    }
                    container actual-holder {
                        uses actual-holder;
                        description    
                "none";
                    }
                    uses local-class;
                    description    
                "Represents a space in an equipment in which another equipment can be fitted in the field.";
                }

            /****************************************
            * package data-types
            **************************************/ 
                typedef connector-and-pin-orientation {
                    type identityref {
                        base CONNECTOR_AND_PIN_ORIENTATION;
                    }
                    description    
                "Most connector schemes are asymmetric such that there are two orientations of the connector where a mating is only possible between two connectors of different orientations. 
                        A multi-pin connector may have a mix of pin orientations. In this case, it is expected that the dominant orientation of pin is chosen for the connector orientation.";
                }
                typedef equipment-category {
                    type identityref {
                        base EQUIPMENT_CATEGORY;
                    }
                    description    
                "The form of equipment.";
                }
                typedef holder-category {
                    type identityref {
                        base HOLDER_CATEGORY;
                    }
                    description    
                "The form of holder.";
                }


        /****************************************
        * package equipment-specification
        **************************************/ 
            /****************************************
            * grouping statements for object classes
            **************************************/ 
                grouping support-constraints {
                    list constrained-supported-non-fru-type {
                        uses supported-non-fru-type;
                        description    
                "none";
                    }
                    list constrained-supported-fru-type {
                        uses supported-equipment-type;
                        description    
                "none";
                    }
                    description    
                "Rules related to how both non-FRU and FRU presence restricts the potential for additional equipments to be installed.
                        An FRU type installed in one holder may limit the FRU types that can be installed in another holder etc.";
                }
                grouping supported-non-fru-type {
                    container non-fru-details {
                        uses equipment;
                        description    
                "none";
                    }
                    list blocked-non-fru-position {
                        min-elements 1;
                        uses non-fru-support-position;
                        description    
                "none";
                    }
                    list support-constraints {
                        uses support-constraints;
                        description    
                "none";
                    }
                    description    
                "The non-FRU equipment types supported by the non-FRU support position.";
                }
                grouping non-fru-support-position {
                    list supported-non-fru-type {
                        min-elements 1;
                        uses supported-non-fru-type;
                        description    
                "none";
                    }
                    description    
                "Equivalent to the holder for the FRU, represents in the specification a place where one or more types of non-FRU could be present. 
                        Unlike the FRU in a Holder, the non-FRU present is fixed in place whilst the equipment is in the field (as it is not Field-replaceable).";
                }
                grouping supported-equipment-type {
                    container fru-details {
                        uses equipment;
                        description    
                "none";
                    }
                    list support-constraints {
                        uses support-constraints;
                        description    
                "none";
                    }
                    list holder {
                        min-elements 1;
                        uses holder;
                        description    
                "none";
                    }
                    description    
                "The FRU equipment types supported by the holder.";
                }


        /****************************************
        * package expected-and-actual
        **************************************/ 
            /****************************************
            * grouping statements for object classes
            **************************************/ 
                grouping actual-holder {
                    uses holder-details;
                    description    
                "A holder in the ActualEquipment.";
                }
                grouping expected-holder {
                    uses holder-details;
                    description    
                "A definition of a holder expected in the ActualEquipment (i.e. an ActualHolder) as part of the constraints provided by the ExpectedEquipment.";
                }
                grouping actual-equipment {
                    uses equipment-detail;
                    description    
                "The equipment that is actually present in the physical network.
                        It will expose all dynamic properties and some critical static properties.";
                }
                grouping expected-equipment {
                    uses equipment-detail;
                    description    
                "A definition of the restrictions on the equipment that is expected to be present in the physical network at a particular 'place'.
                        The expected equipment will state the type and may constrain any other invariant properties. 
                        It may also provide desired ranges for dynamic properties.";
                }


        /****************************************
        * package connector-and-pin
        **************************************/ 
            /****************************************
            * grouping statements for object classes
            **************************************/ 
                grouping pin {
                    container position {
                        uses position;
                        description    
                "none";
                    }
                    leaf orientation {
                        type connector-and-pin-orientation;
                        description    
                    "none";
                    }
                    description    
                "An individual physical connection point (male or female) that is not relevantly divisible.
                        May be capable of carrying electrical or optical signals. 
                        A pin normally has only one wire/fiber strand attached. 
                        It may have more than one wire/fiber attached but is such that the attachment forms a physical merge (all attached things receive exactly the same signal and any inputs to the pin are electrically/optically merged).";
                }
                grouping pin-group {
                    leaf-list pin {
                        type leafref {
                            pathmust "/core-model:field-replaceable/core-model:connector/core-model:pin/core-model:";
                    require-instance false;
                        }
                must  'deref(.) = current()';
                        min-elements 1;
                        description     
                 "none";
                    }
                    description    
                "A group of pins relevant for some purpose.";
                }
                grouping pin-layout {
                    list position {
                        min-elements 1;
                        uses position;
                        description    
                "none";
                    }
                    description    
                "The structuring of pins in a connector.";
                }
                grouping access-port {
                    uses pin-group;
                    description    
                "A group of pins that together support a signal group where any one pin removed from the group will prevent all signals of the signal group from flowing successfully.";
                }
                grouping signal-ref-pt {
                    container ltp {
                        uses logical-termination-point;
                        description    
                "none";
                    }
                    list elemental-signals {
                        min-elements 1;
                        uses elemental-signals;
                        description    
                "none";
                    }
                    description    
                "A single coherent signal as processed by a single LTP.";
                }
                grouping signal-ref-pt-group {
                    container access-port {
                        uses access-port;
                        description    
                "none";
                    }
                    leaf-list signal-ref-pt {
                        type leafref {
                            pathmust "/core-model:signal-ref-pt/core-model:";
                    require-instance false;
                        }
                must  'deref(.) = current()';
                        min-elements 1;
                        description     
                 "none";
                    }
                    description    
                "A conceptual access for a group of signals (where that group of signals cannot be separated).
                        A physical indivisible group of signals.";
                }
                grouping elemental-signals {
                    list pin {
                        min-elements 1;
                        uses pin;
                        description    
                "none";
                    }
                    description    
                "The elemental (sub-atomic) parts of an 'indivisible' signal where processing in the LTP is required to extract the elemental signals.";
                }
                grouping group-of-pins {
                    description    
                "A group of pins from one or more connectors relevant for some purpose.";
                }
                grouping group-of-strands {
                    description    
                "A group of strands from one or more cables relevant for some purpose";
                }
                grouping multiple-strand-span {
                    list access-port {
                        min-elements 2;
                        uses access-port;
                        description    
                "none";
                    }
                    leaf-list strand {
                        type leafref {
                            pathmust "/core-model:cable/core-model:bundled-cable/core-model:strand/core-model:";
                    require-instance false;
                        }
                must  'deref(.) = current()';
                        min-elements 1;
                        description     
                 "none";
                    }
                    uses group-of-strands;
                    description    
                "An adjacency between AccessPorts. 
                        The adjacency is supported by a group of strands between pins of the AccessPorts.
                        This is a physical abstraction.";
                }
                grouping strand {
                    list pin {
                        max-elements 2;
                        uses pin;
                        description    
                "none";
                    }
                    leaf-list adjacentstrand {
                        type leafref {
                            pathmust "/core-model:cable/core-model:bundled-cable/core-model:strand/core-model:";
                    require-instance false;
                        }
                must  'deref(.) = current()';
                        description     
                 "none";
                    }
                    leaf-list spliced-strand {
                        type leafref {
                            pathmust "/core-model:cable/core-model:bundled-cable/core-model:strand/core-model:";
                    require-instance false;
                        }
                must  'deref(.) = current()';
                        max-elements 2;
                        description     
                 "none";
                    }
                    leaf strand-media-characteristics {
                        type string;
                        description    
                    "none";
                    }
                    description    
                "A Strand represents a continuous long, thin piece of a medium such as glass fiber or copper wire.
                        In this model a Strand:
                        - a strand has two ends
                        - a splice can only be between 2 strands.
                        - the end of a strand may have a splice, a connector or be hidden
                        - only one end can be hidden in an equipment
                        - where a cable has more than two end each strand only goes between two of the ends
                        This model does NOT account for multiple copper strands being spliced.";
                }


        /****************************************
        * package equipment-to-function
        **************************************/ 
            /****************************************
            * grouping statements for object classes
            **************************************/ 
                grouping aggregate-function {
                    leaf-list atomic-function {
                        type leafref {
                            pathmust "/core-model:equipment/core-model:encapsulated-non-fru/core-model:function-block/core-model:atomic-function/core-model:";
                    require-instance false;
                        }
                must  'deref(.) = current()';
                        description     
                 "none";
                    }
                    list function-block {
                        uses function-block;
                        description    
                "none";
                    }
                    list atomic-function-view {
                        uses atomic-function;
                        description    
                "none";
                    }
                    description    
                "Represents some assembly of atomic functions that can be considered as useful from some perspective. Can be viewed as one or more functional blocks (essential leading to a recursive cycle of Block --> Atomic --> Aggregate --> Block). 
                        Each of the functional entities in the model is a view of a single AggregateFunction.";
                }
                grouping atomic-function {
                    list aggregate-function {
                        uses aggregate-function;
                        description    
                "none";
                    }
                    description    
                "Represents the micro-function that is the largest function of the functional block that will not need to be subdivided when forming the relevant abstract views (i.e., it can just be assembled).";
                }
                grouping function-block {
                    list atomic-function {
                        uses atomic-function;
                        description    
                "none";
                    }
                    list equipment {
                        uses equipment;
                        description    
                "none";
                    }
                    description    
                "Represents the chunks of base functionality provided by the equipment.
                        The chunks of base functionality are likely to relate to the hardware layout and be quite distinct from the functions of the familiar abstract representation.
                        The functions are necessarily abstract and, to a degree, virtualized.";
                }
                grouping resilient-function-block {
                    list atomic-function {
                        uses atomic-function;
                        description    
                "none";
                    }
                    description    
                "Represents the functions emergent from a function protection process.
                        The emergent functions are necessarily significantly virtualized.";
                }
                grouping resilience-selector {
                    container resilient-function-block {
                        uses resilient-function-block;
                        description    
                "none";
                    }
                    list function-block {
                        min-elements 2;
                        uses function-block;
                        description    
                "none";
                    }
                    description    
                "Represents the ability to select capability from two or more identical FunctionalBlocks so as to give rise to an equivalent emergent resilient function.";
                }



    /****************************************
    * package core-specification-model
    **************************************/ 
        /****************************************
        * package fc-capability
        **************************************/ 
            /****************************************
            * grouping statements for object classes
            **************************************/ 
                /****************************************
                * package fc-capability-core
                **************************************/ 
                    grouping configuration-and-switch-controller-spec {
                        list switch-control-rule {
                            min-elements 1;
                            uses control-rule;
                            description    
                "none";
                        }
                        leaf-list ingress-switch-selection {
                            type string;
                            description     
                 "none";
                        }
                        leaf-list egress-switch-selection {
                            type string;
                            description     
                 "none";
                        }
                        uses global-class;
                        description    
                "The spec of a ConfigurationAndSwitchController.";
                    }
                    grouping egress-port-set {
                        uses local-class;
                        description    
                "The grouping of FC egress ports that have the same behavior and relationship to the switch etc.
                            Will carry rules for the grouping.";
                    }
                    grouping forwarding-spec {
                        list multi-switched-uni-flow {
                            uses multi-switched-uni-flow;
                            description    
                "none";
                        }
                        list casc-spec {
                            uses configuration-and-switch-controller-spec;
                            description    
                "none";
                        }
                        list port-set-spec {
                            min-elements 1;
                            uses port-set-spec;
                            description    
                "none";
                        }
                        container configuration-group-spec-spec {
                            uses configuration-group-spec;
                            description    
                "none";
                        }
                        container ltp-association-rule {
                            uses ltp-association-rule;
                            description    
                "none";
                        }
                        leaf-list layer-protocol-parameter-spec {
                            type leafref {
                                pathmust "/core-model:layer-protocol-parameter-spec/core-model:";
                    require-instance false;
                            }
                must  'deref(.) = current()';
                            description     
                 "none";
                        }
                        leaf spec-target-class {
                            type metaclass-class-name;
                            description    
                    "The name of the class (e.g. ForwardingConstruct) to which the specification applies.";
                        }
                        list forwarding-occurrence {
                            uses forwarding-occurrence;
                            description    
                "none";
                        }
                        list lp-occurrence-in-fc-spec {
                            uses lp-occurrence-in-fc-spec;
                            description    
                "none";
                        }
                        list casc-occurrence-in-fc-spec {
                            uses casc-occurrence-in-fc-spec;
                            description    
                "none";
                        }
                        uses global-class;
                        description    
                "The overall spec for the forwarding entity.";
                    }
                    grouping ingress-port-set {
                        uses local-class;
                        description    
                "The grouping of FC ingress ports that have the same behavior and relationship to the switch etc.
                            Will carry rules for the grouping.";
                    }
                    grouping multi-switched-uni-flow {
                        list ingress-port-set {
                            min-elements 1;
                            uses ingress-port-set;
                            description    
                "none";
                        }
                        list egress-port-set {
                            min-elements 1;
                            uses egress-port-set;
                            description    
                "none";
                        }
                        container casc-spec {
                            uses configuration-and-switch-controller-spec;
                            description    
                "none";
                        }
                        container ingress-fc-port-set {
                            uses ingress-port-set;
                            description    
                "none";
                        }
                        container egress-fc-port-set {
                            uses egress-port-set;
                            description    
                "none";
                        }
                        leaf layer-protocol-parameter-spec {
                            type leafref {
                                pathmust "/core-model:layer-protocol-parameter-spec/core-model:";
                    require-instance false;
                            }
                must  'deref(.) = current()';
                            description    
                    "none";
                        }
                        uses local-class;
                        description    
                "A switched unidirectional forwarding element that can take one or more inputs and switch to one or more outputs.
                            The switch can also be open (high impedance).";
                    }
                    grouping port-set-spec {
                        list ingress-port-set {
                            uses ingress-port-set;
                            description    
                "none";
                        }
                        list egress-port-set {
                            uses egress-port-set;
                            description    
                "none";
                        }
                        container ltp-association-rule {
                            uses ltp-association-rule;
                            description    
                "none";
                        }
                        leaf role {
                            type port-role;
                            default "true";
                            description    
                    "Role of the port in the context of the ForwardingSpec.";
                        }
                        leaf layer-protocol-parameter-spec {
                            type leafref {
                                pathmust "/core-model:layer-protocol-parameter-spec/core-model:";
                    require-instance false;
                            }
                must  'deref(.) = current()';
                            description    
                    "none";
                        }
                        leaf is-internal-port {
                            type boolean;
                            config false;
                            description    
                    "The FcPort is not exposed and cannot have associated LTPs.
                                This form of FcPort is used to enable chaining of FcSwitches or FcRoutes in complex network protection scenarios.";
                        }
                        list forwarding-port-occurrence {
                            uses forwarding-port-occurrence;
                            description    
                "none";
                        }
                        uses local-class;
                        description    
                "The specification of a set of equivalent port of the forwarding entity.
                            For example, there may be a several ports with exactly the same behavior with respect to each other and with respect to all other ports. These can all reference one PortSetSpec. 
                            In a symmetric FC this means one PortsSetSpec can be used for all ports.";
                    }
                    grouping control-rule {
                        uses local-class;
                        description    
                "A rule describes the bounds of the behavior of a CASC.";
                    }

                /****************************************
                * package fc-capability-additional
                **************************************/ 
                    grouping configuration-group-spec {
                        container casc {
                            uses configuration-and-switch-controller-spec;
                            description    
                "none";
                        }
                        list forwarding-spec {
                            min-elements 1;
                            uses forwarding-spec;
                            description    
                "none";
                        }
                        container ltp-association-rule {
                            uses ltp-association-rule;
                            description    
                "none";
                        }
                        uses global-class;
                        description    
                "The specification of the grouping rules for a particular configuration of FCs and CASCs.";
                    }
                    grouping ltp-association-rule {
                        uses local-class;
                        description    
                "Rules for the association from the port spec to LTPs identifying restrictions of use.";
                    }

                /****************************************
                * package occurrences-in-fc-spec
                **************************************/ 
                    grouping casc-occurrence-in-fc-spec {
                        list casc-port-occurence {
                            min-elements 1;
                            uses casc-port-occurrence-in-fc-spec;
                            description    
                "none";
                        }
                        description    
                "A CASC component that is part of a system of components that represents the behavior of an FC/ForwardingOccurrence.";
                    }
                    grouping casc-port-occurrence-in-fc-spec {
                        description    
                "Port of a CascOccurrence where the port may be bound to a port of an LpOccurrence.
                            This port may NOT be exposed as a port on the containing FC/ForwardingOccurrence.";
                    }
                    grouping forwarding-occurrence {
                        list forwarding-port-occurence {
                            min-elements 2;
                            uses forwarding-port-occurrence;
                            description    
                "none";
                        }
                        container forwarding-spec {
                            uses forwarding-spec;
                            description    
                "none";
                        }
                        description    
                "A forwarding component that is part of a system of components that represents the behavior of an FC or a ForwardingOccurrence at a higher abstraction (leading to an FC).";
                    }
                    grouping forwarding-port-occurrence {
                        leaf forwarding-port-occurence {
                            type leafref {
                                pathmust "/core-model:configuration-group-spec/core-model:forwarding-spec/core-model:forwarding-occurrence/core-model:forwarding-port-occurence/core-model:";
                    require-instance false;
                            }
                must  'deref(.) = current()';
                            description    
                    "none";
                        }
                        container lp-port-occurrence {
                            uses lp-port-occurrence-in-fc-spec;
                            description    
                "none";
                        }
                        container port-set-spec {
                            uses port-set-spec;
                            description    
                "none";
                        }
                        description    
                "Port of a ForwardingOccurrence where the port may be bound to another port of another ForwardingOccurrence or to another component or may be exposed as a port on the containing FC/ForwardingOccurrence.";
                    }
                    grouping lp-occurrence-in-fc-spec {
                        list lp-port-occurrence {
                            min-elements 1;
                            uses lp-port-occurrence-in-fc-spec;
                            description    
                "none";
                        }
                        container lp-spec {
                            uses lp-spec;
                            description    
                "none";
                        }
                        description    
                "A termination component that is part of a system of components that represents the behavior of an FC/ForwardingOccurrence.";
                    }
                    grouping lp-port-occurrence-in-fc-spec {
                        container casc-port-occurrence {
                            uses casc-port-occurrence-in-fc-spec;
                            description    
                "none";
                        }
                        container lp-port-spec {
                            uses lp-port-spec;
                            description    
                "none";
                        }
                        leaf lp-port-occurrence {
                            type leafref {
                                pathmust "/core-model:configuration-group-spec/core-model:forwarding-spec/core-model:lp-occurrence-in-fc-spec/core-model:lp-port-occurrence/core-model:";
                    require-instance false;
                            }
                must  'deref(.) = current()';
                            description    
                    "none";
                        }
                        description    
                "Port of a LpOccurrence where the port may be bound to another port of another LpOccurrence, a port of a ForwardingOccurrence or to another component.
                            This port may NOT be exposed as a port on the containing FC/ForwardingOccurrence.";
                    }


            /****************************************
            * package associations
            **************************************/ 


        /****************************************
        * package forwarding-domain-and-link-capability
        **************************************/ 
            /****************************************
            * grouping statements for object classes
            **************************************/ 
                grouping fd-and-link-rule {
                    leaf rule-type {
                        type rule-type;
                        description    
                    "Indicates how to interpret the rule statements.";
                    }
                    leaf forwarding-rule {
                        type forwarding-rule;
                        description    
                    "The specific forwarding capability.";
                    }
                    leaf-list complex-rule-qualifier {
                        type to-be-defined;
                        description     
                 "complexRuleQualifier is used to modulate the rule.
                            complexRuleQualifier covers case such as same channel but can reference any property of the FD, of the associated LTP and of the FC instance to be created.
                            Qualifier should be capable of expressing rule interaction.
                            Provides restrictions (such as same channel).
                            Note: May be better to have a same index/any index explicit rule.
                            Could have 'property=x' valueEquation=same, increment, etc.";
                    }
                    leaf fc-spec {
                        type to-be-defined;
                        description    
                    "Indicates the type(s) of FC to which the rule applies.";
                    }
                    list fc-port-role {
                        uses port-role-rule;
                        description    
                "Indicates the port role to which the rule applies. 
                            If an FD carries a port role that role applies also to the associated Link rules.
                            fcPortRole corresponded to role defined in the FcSpec. This is a list with rule opportunity. No port role statement means all port roles are allowed.";
                    }
                    leaf-list fc-port-direction {
                        type port-direction;
                        description     
                 "fcPortDirection is a list of FcPortDirection.";
                    }
                    leaf override-priority {
                type int64;
                        description    
                    "overridePriority allows for one rule set to override another.";
                    }
                    leaf signal-property {
                        type to-be-defined;
                        description    
                    "The rule only applies to signals with the properties listed. 
                            If the attribute is not present then the rule applies to all signals.";
                    }
                    list fc-spec-reference-class-ref {
                        if-feature spectargetclass-forwardingconstruct;
                        uses metaclass-class;
                        description    
                "none";
                    }
                    description    
                "Set of 'AND' rules related to creation of FCs across the FD/Link (i.e., all rules have to be met for the FC creation to be allowed).
                        Embedded conditions all have to be met and hence are AND. Elements of the list attributes are ORs.
                        Absence fcSpec NOT valid for FORWARDING rules (only valid for cost/risk etc. rules).
                        Absence of FcPortRole means all roles for referenced spec.
                        Absence of direction means all directions.";
                }
                grouping fd-and-link-rule-set {
                    leaf-list fd-rule {
                        type leafref {
                            pathmust "/core-model:fd-and-link-rule/core-model:";
                    require-instance false;
                        }
                must  'deref(.) = current()';
                        min-elements 1;
                        description     
                 "none";
                    }
                    leaf is-rule-only {
                        type boolean;
                        description    
                    "Indicates that the FD is only carrying rules and that FC creation is the FD is NOT allowed.";
                    }
                    leaf layer-protocol-parameter-spec {
                        type leafref {
                            pathmust "/core-model:layer-protocol-parameter-spec/core-model:";
                    require-instance false;
                        }
                must  'deref(.) = current()';
                        description    
                    "none";
                    }
                    description    
                "Set of 'OR' rules related to creation of FCs across the FD/Link (i.e. only one of the rules have to be met for the FC creation to be allowed).
                        Absence of RuleSet means 'Any', i.e. all points, all FcTypes etc.
                        Presence of RuleSet means possibilities must all be defined by rules
                        Absence of forwardingRule means no explicit stated possibilities.
                        No capacity statement means no capacity restrictions.
                        ";
                }

/****************************************
* typedef statements
**************************************/ 
                typedef forwarding-rule {
                    type identityref {
                        base FORWARDING_RULE;
                    }
                    description    
                "Rule that restricts the creation/deletion of an FC between points grouped by FD or related by the Link between FDs.";
                }
                typedef rule-type {
                    type identityref {
                        base RULE_TYPE;
                    }
                    description    
                "Indicates the focus of the rule.";
                }
                typedef port-role-rule-option {
                    type identityref {
                        base PORT_ROLE_RULE_OPTION;
                    }
                    description    
                "Indicates how to interpret the PortRole list.";
                }
                typedef signal-property-value-rule {
                    type identityref {
                        base SIGNAL_PROPERTY_VALUE_RULE;
                    }
                    description    
                "none";
                }

/*********************************************
* grouping statements for complex data types
*******************************************/ 
                identity PORT_DIRECTION {
                    description    
                "none";
                }
                identity PORT_DIRECTION_BIDIRECTIONAL {
                    base PORT_DIRECTION;
                    description    
                "The Port has both an INPUT flow and an OUTPUT flow defined.";
                }
                identity PORT_DIRECTION_INPUT {
                    base PORT_DIRECTION;
                    description    
                "The Port only has definition for a flow into the Forwarding entity (i.e. an ingress flow).";
                }
                identity PORT_DIRECTION_OUTPUT {
                    base PORT_DIRECTION;
                    description    
                "The Port only has definition for a flow out of the Forwarding entity (i.e. an egress flow).";
                }
                identity PORT_DIRECTION_UNIDENTIFIED_OR_UNKNOWN {
                    base PORT_DIRECTION;
                    description    
                "Not a normal state. The system is unable to determine the correct value.";
                }
                identity PORT_DIRECTION_OMNIDIRECTIONAL {
                    base PORT_DIRECTION;
                    description    
                "none";
                }
                identity FORWARDING_DIRECTION {
                    description    
                "none";
                }
                identity FORWARDING_DIRECTION_BIDIRECTIONAL {
                    base FORWARDING_DIRECTION;
                    description    
                "The Forwarding entity supports both BIDIRECTIONAL flows at all Ports (i.e. all Ports have both an INPUT flow and an OUTPUT flow defined).";
                }
                identity FORWARDING_DIRECTION_UNIDIRECTIONAL {
                    base FORWARDING_DIRECTION;
                    description    
                "The Forwarding entity has Ports that are either INPUT or OUTPUT. It has no BIDIRECTIONAL Ports.";
                }
                identity FORWARDING_DIRECTION_UNDEFINED_OR_UNKNOWN {
                    base FORWARDING_DIRECTION;
                    description    
                "Not a normal state. The system is unable to determine the correct value.";
                }
                identity FORWARDING_DIRECTION_OMNIDIRECTIONAL {
                    base FORWARDING_DIRECTION;
                    description    
                "none";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base TERMINATION_DIRECTION;
                    description    
                "Not a normal state. The system is unable to determine the correct value.";
                }
                identity EXTENDED_TERMINATION_DIRECTION {
                    description    
                "none";
                }
                identity EXTENDED_TERMINATION_DIRECTION_CONTRA_DIRECTION_SINK {
                    base EXTENDED_TERMINATION_DIRECTION;
                    description    
                "The essential flow of the Termination entity is SINK (i.e. up the layer stack) but the INPUT flow of the Termination entity was provided by a SOURCE OUTPUT or taken from a SOURCE INPUT (duplicating the input signal) hence reversing the flow orientation from down the layer stack to up the layer stack.";
                }
                identity EXTENDED_TERMINATION_DIRECTION_CONTRA_DIRECTION_SOURCE {
                    base EXTENDED_TERMINATION_DIRECTION;
                    description    
                "The essential flow of the Termination entity is SOURCE (i.e. down the layer stack) but the OUTPUT flow of the Termination entity was fed to (and replaces) a SINK OUTPUT or was fed to a SINK INPUT (replacing the normal flow) hence reversing the flow orientation from down the layer stack to up the layer stack.";
                }
                identity TERMINATION_STATE {
                    description    
                "none";
                }
                identity TERMINATION_STATE_LP_CAN_NEVER_TERMINATE {
                    base TERMINATION_STATE;
                    description    
                "A non-flexible case that can never be terminated.";
                }
                identity TERMINATION_STATE_LP_NOT_TERMINATED {
                    base TERMINATION_STATE;
                    description    
                "A flexible termination that can terminate but is currently not terminated.";
                }
                identity TERMINATION_STATE_TERMINATED_SERVER_TO_CLIENT_FLOW {
                    base TERMINATION_STATE;
                    description    
                "A flexible termination that is currently terminated for server to client flow only.";
                }
                identity TERMINATION_STATE_TERMINATED_CLIENT_TO_SERVER_FLOW {
                    base TERMINATION_STATE;
                    description    
                "A flexible termination that is currently terminated for client to server flow only.";
                }
                identity TERMINATION_STATE_TERMINATED_BIDIRECTIONAL {
                    base TERMINATION_STATE;
                    description    
                "A flexible termination that is currently terminated in both directions of flow.";
                }
                identity TERMINATION_STATE_LP_PERMENANTLY_TERMINATED {
                    base TERMINATION_STATE;
                    description    
                "A non-flexible termination that is always terminated (in both directions of flow for a bidirectional case and in the one direction of flow for both unidirectional cases).";
                }
                identity TERMINATION_STATE_TERMINATION_STATE_UNKNOWN {
                    base TERMINATION_STATE;
                    description    
                "There TerminationState cannot be determined.";
                }
                identity PROTECTION_REASON {
                    description    
                "none";
                }
                identity PROTECTION_REASON_WAIT_TO_REVERT {
                    base PROTECTION_REASON;
                    description    
                "The resource is selected as control is waiting to restore to a preferred resource.";
                }
                identity PROTECTION_REASON_SIGNAL_DEGRADE {
                    base PROTECTION_REASON;
                    description    
                "The resource is selected as the best preferred resource is in signal degrade.";
                }
                identity PROTECTION_REASON_SIGNAL_FAIL {
                    base PROTECTION_REASON;
                    description    
                "The resource is selected as the best preferred resource is in signal fail.";
                }
                identity ROUTE_SELECTION_CONTROL {
                    description    
                "none";
                }
                identity ROUTE_SELECTION_CONTROL_LOCK_OUT {
                    base ROUTE_SELECTION_CONTROL;
                    description    
                "The resource is configured to temporarily not be available for use in the protection scheme(s) it is part of.
                        This overrides all other protection control states including forced.
                        If the item is locked out, then it cannot be used under any circumstances.
                        Note: Only relevant when part of a protection scheme.
                        Note: if a protection process that has a relationship to the item (i.e. is one of the options the protection process may choose) is deactivated by being isFrozen = true) then the lockout request will be rejected. ";
                }
                identity ROUTE_SELECTION_REASON {
                    description    
                "none";
                }
                identity SWITCH_CONTROL {
                    description    
                "none";
                }
                identity SWITCH_CONTROL_NORMAL {
                    base SWITCH_CONTROL;
                    description    
                "No administrative control applied to the switch.";
                }
                identity SWITCH_CONTROL_MANUAL {
                    base SWITCH_CONTROL;
                    description    
                "Resource temporarily chosen by control configuration where the resource is not the preferred resource.
                        Preferred resource has highest priority.
                        Temporarily overrides reversion.
                        If this resource fails, it will switch to best available resource. 
                        If resource selected is shared and another FC requires the resource, then the selection control will change to Normal and switch to best available based upon normal rules.
                        Cannot manually switch a Forced switch, cannot remove a forced switch, cannot switch to a locked out item and will be rejected if the protection process is deactivated by being Freeze = true).
                        A manual switch/route that is selecting an FcPort, LTP, FC, Link or Route that is subsequently set to LOCK_OUT will have the manual removed (changed to NORMAL) and will switch away from the FcPort with LOCK_OUT to best available based upon normal rules.
                        A manual switch that is selecting an FcPort that is subsequently selected by a Forced switch will be restored to normal operation and the manual will be removed.
                        A manual switch/route that is selecting an FcPort, LTP, FC, Link or Route that is subsequently manual selected by another switch/route will have the manual removed and will switch away from the FcPort.
                        Can be returned to NORMAL by configuration action.";
                }
                identity SWITCH_CONTROL_FORCED {
                    base SWITCH_CONTROL;
                    description    
                "Resource temporarily chosen by control configuration where the resource is not the preferred resource.
                        Preferred resource has highest priority.
                        Temporarily overrides reversion.
                        If this resource fails it will NOT switch. 
                        If resource selected is shared and another FC requires the resource through a FORCE on that FC and the FC is of a higher FcPriority then the selection control on this FC will change to NORMAL and switch to best available based upon normal rules.
                        If the resource selected is then set to LOCK_OUT then the selection control will change to NORMAL and switch to best available based upon normal rules.
                        Can be returned to NORMAL by configuration action.";
                }
                identity SWITCH_STATE_REASON {
                    description    
                "none";
                }
                identity REVERSION_MODE {
                    description    
                "none";
                }
                identity REVERSION_MODE_REVERTIVE {
                    base REVERSION_MODE;
                    description    
                "An FC switched to a lower priority (non-preferred) resource will revert to a higher priority (preferred) resource when that recovers (potentially after some hold-off time).";
                }
                identity REVERSION_MODE_NON-REVERTIVE {
                    base REVERSION_MODE;
                    description    
                "An FC switched to a lower priority (non-preferred) resource will not revert to a higher priority (preferred) resource when that recovers.";
                }
                identity RESILIENCE_CONTROL {
                    description    
                "none";
                }
                identity RESILIENCE_CONTROL_QUIESCENT {
                    base RESILIENCE_CONTROL;
                    description    
                "none";
                }
                identity RESILIENCE_CONTROL_RESTORING {
                    base RESILIENCE_CONTROL;
                    description    
                "none";
                }
                identity RESILIENCE_CONTROL_RECOVERY_FAILED {
                    base RESILIENCE_CONTROL;
                    description    
                "none";
                }
                identity RESILIENCE_CONTROL_UNKNOWN {
                    base RESILIENCE_CONTROL;
                    description    
                "none";
                }
                identity RUN_MODE {
                    description    
                "none";
                }
                identity RUN_MODE_FREE_RUN {
                    base RUN_MODE;
                    description    
                "The clock is not synchronized to another clock.";
                }
                identity RUN_MODE_LOCKED {
                    base RUN_MODE;
                    description    
                "The clock is synchronized to another clock.";
                }
                identity RUN_MODE_HOLD_OVER {
                    base RUN_MODE;
                    description    
                "The clock was previously synchronized to another clock but that timing input has been lost.
                        The clock is set to the last known synchronization.";
                }
                identity LAYER_PROTOCOL_NAME {
                    description    
                "none";
                }
                identity LAYER_PROTOCOL_NAME_PHOTONIC_MEDIA {
                    base LAYER_PROTOCOL_NAME;
                    description    
                "The characteristic information is that of a channel able to carry photons and of the photon source/sink.";
                }
                identity LAYER_PROTOCOL_NAME_OTU_AND_ODU {
                    base LAYER_PROTOCOL_NAME;
                    description    
                "The characteristic information is that of a channel able to carry ODU/OTU protocol (OTN) and of the ODU/OTU source/sink.";
                }
                identity LAYER_PROTOCOL_NAME_ETHERNET {
                    base LAYER_PROTOCOL_NAME;
                    description    
                "The characteristic information is that of a channel able to carry Ethernet protocol and of the Ethernet protocol source/sink.";
                }
                identity OPERATIONAL_STATE {
                    description    
                "none";
                }
                identity OPERATIONAL_STATE_DISABLED {
                    base OPERATIONAL_STATE;
                    description    
                "The resource is unable to meet the SLA of the user of the resource. 
                        If no (explicit) SLA is defined the resource is disabled if it is totally inoperable and unable to provide service to the user.";
                }
                identity OPERATIONAL_STATE_ENABLED {
                    base OPERATIONAL_STATE;
                    description    
                "The resource is partially or fully operable and available for use.";
                }
                identity ADMINISTRATIVE_STATE {
                    description    
                "none";
                }
                identity ADMINISTRATIVE_STATE_LOCKED {
                    base ADMINISTRATIVE_STATE;
                    description    
                "Users are administratively prohibited from making use of the resource.";
                }
                identity ADMINISTRATIVE_STATE_UNLOCKED {
                    base ADMINISTRATIVE_STATE;
                    description    
                "Users are allowed to use the resource.";
                }
                identity ADMINISTRATIVE_STATE_SHUTTING_DOWN {
                    base ADMINISTRATIVE_STATE;
                    description    
                "The entity is administratively restricted to existing instances of use only. There may be specific actions to remove existing uses. No new instances of use can be enabled.
                        The resource automatically transitions to “locked” when the last user quits. 
                        The administrative state is not visible in the client context. 
                        The lifecycle state “pending removal” should be used to indicate to the client that the provider intends to remove the resource.";
                }
                identity ADMINISTRATIVE_CONTROL {
                    description    
                "none";
                }
                identity ADMINISTRATIVE_CONTROL_UNLOCK {
                    base ADMINISTRATIVE_CONTROL;
                    description    
                "The intention is for the entity to become unlocked.
                        The entity may already be UNLOCKED.";
                }
                identity ADMINISTRATIVE_CONTROL_LOCK_PASSIVE {
                    base ADMINISTRATIVE_CONTROL;
                    description    
                "The intention is for the entity to become locked but no effort is expected to move to the Locked state (the state will be achieved once all users stop using the resource). 
                        The entity may be LOCKED.";
                }
                identity ADMINISTRATIVE_CONTROL_LOCK_ACTIVE {
                    base ADMINISTRATIVE_CONTROL;
                    description    
                "The intention is for the entity to become locked and it is expected that effort will be made to move to the Locked state (users will be actively removed). 
                        The entity may already be LOCKED.";
                }
                identity ADMINISTRATIVE_CONTROL_LOCK_IMMEDIATE {
                    base ADMINISTRATIVE_CONTROL;
                    description    
                "The intention is for the entity to become locked and it is expected to move to the Locked state immediately (users will be force removed). 
                        The entity may already be LOCKED.";
                }
                identity ADMINISTRATIVE_CONTROL_QUIESCENT {
                    base ADMINISTRATIVE_CONTROL;
                    description    
                "The administrative state is at a stable value (LOCKED/UNLOCKED) and no action is being taken.";
                }
                identity LIFECYCLE_STATE {
                    description    
                "none";
                }
                identity LIFECYCLE_STATE_PLANNED {
                    base LIFECYCLE_STATE;
                    description    
                "The resource is planned but is not present in the network.
                        Should include a 'time' when the resources are expected to be installed.";
                }
                identity LIFECYCLE_STATE_POTENTIAL_AVAILABLE {
                    base LIFECYCLE_STATE;
                    description    
                "The supporting resources are present in the network but are shared with other clients; or require further configuration before they can be used; or both.
                        (1) When a potential resource is configured and allocated to a client it is moved to the INSTALLED state for that client.
                        (2) If the potential resource has been consumed (e.g. allocated to another client) it is moved to the POTENTIAL BUSY state for all other clients.";
                }
                identity LIFECYCLE_STATE_POTENTIAL_BUSY {
                    base LIFECYCLE_STATE;
                    description    
                "The supporting resources are present in the network but have been allocated to other clients.";
                }
                identity LIFECYCLE_STATE_INSTALLED {
                    base LIFECYCLE_STATE;
                    description    
                "The resource is present in the network and is capable of providing the service.";
                }
                identity LIFECYCLE_STATE_PENDING_REMOVAL {
                    base LIFECYCLE_STATE;
                    description    
                "The resource has been marked for removal. Should include a “time” when the resources are expected to be removed.";
                }
                identity BLOCK_DIRECTION {
                    description    
                "none";
                }
                identity BLOCK_DIRECTION_NO_BLOCK {
                    base BLOCK_DIRECTION;
                    description    
                "The FC is not blocking signal related to the LTP.";
                }
                identity BLOCK_DIRECTION_INGRESS_BLOCK {
                    base BLOCK_DIRECTION;
                    description    
                "The FC is blocking signal that is flowing into the LTP from the FC.";
                }
                identity BLOCK_DIRECTION_EGRESS_BLOCK {
                    base BLOCK_DIRECTION;
                    description    
                "The FC is blocking signal flowing out of the LTP to the FC.";
                }
                identity BLOCK_DIRECTION_BIDIRECTIONAL_BLOCK {
                    base BLOCK_DIRECTION;
                    description    
                "The FC is blocking both directions of traffic, i.e. Ingress and Egress, to/from the LTP.";
                }
                identity CONNECTOR_AND_PIN_ORIENTATION {
                    description    
                "none";
                }
                identity CONNECTOR_AND_PIN_ORIENTATION_MALE {
                    base CONNECTOR_AND_PIN_ORIENTATION;
                    description    
                "The connecting elements are dominantly protrusions.";
                }
                identity CONNECTOR_AND_PIN_ORIENTATION_FEMALE {
                    base CONNECTOR_AND_PIN_ORIENTATION;
                    description    
                "The connecting elements are dominantly indentations.";
                }
                identity CONNECTOR_AND_PIN_ORIENTATION_SYMMETRIC_NEUTRAL {
                    base CONNECTOR_AND_PIN_ORIENTATION;
                    description    
                "The pin (and housing) orientation combination is such that it is symmetric so a connector is compatible with itself.
                        The connecting element may be a surface rather than protrusions or indentations.";
                }
                identity EQUIPMENT_CATEGORY {
                    description    
                "none";
                }
                identity EQUIPMENT_CATEGORY_SUBRACK {
                    base EQUIPMENT_CATEGORY;
                    description    
                "An assembly with holders designed to accommodate CIRCUIT_PACKs. 
                        The assembly is designed to be mounted in a RACK.";
                }
                identity EQUIPMENT_CATEGORY_CIRCUIT_PACK {
                    base EQUIPMENT_CATEGORY;
                    description    
                "An assembly with connectors compatible with those in a holder.
                        The assembly is designed to be mounted in a holder (SLOT) of a SUBRACK.
                        May also support holders (SLOTs) for SMALL_FORMFACTOR_PLUGGABLEs.";
                }
                identity EQUIPMENT_CATEGORY_SMALL_FORMFACTOR_PLUGGABLE {
                    base EQUIPMENT_CATEGORY;
                    description    
                "A small assembly (compared to a CIRCUIT_PACK) with connectors compatible with those in a holder.
                        The assembly is designed to be mounted in a holder (SLOT) of a CIRCUIT_PACK or STAND_ALONE_UNIT.";
                }
                identity EQUIPMENT_CATEGORY_STAND_ALONE_UNIT {
                    base EQUIPMENT_CATEGORY;
                    description    
                "An assembly with connectors for cabling and potentially with holders.
                        The assembly is designed to be mounted in a freeform environment (on a table or simple mechanical cabinet).
                        May support holders (SLOTs) for CIRCUIT_PACKs or for SMALL_FORMFACTOR_PLUGGABLEs.";
                }
                identity EQUIPMENT_CATEGORY_RACK {
                    base EQUIPMENT_CATEGORY;
                    description    
                "A mechanical assembly with cabling and predefined mounting points for particular SUBRACK types.
                        The assembly is designed to be mounted on the floor in a row with other RACKs.";
                }
                identity HOLDER_CATEGORY {
                    description    
                "none";
                }
                identity HOLDER_CATEGORY_SLOT {
                    base HOLDER_CATEGORY;
                    description    
                "A guided holder with fixed connectors.
                        The guided holder is designed to take a particular form of CIRCUIT_PACK or SMALL_FORMFACTOR_PLUGGABLE";
                }
                identity FORWARDING_RULE {
                    description    
                "none";
                }
                identity FORWARDING_RULE_CANNOT_FORWARD_ACROSS_FD_LINK {
                    base FORWARDING_RULE;
                    description    
                "LTPs referenced by the FD (or indirectly by the Link between FDs) cannot have FCs created between them.
                        This rule overrides all others.";
                }
                identity FORWARDING_RULE_MUST_FORWARD_ACROSS_FD_LINK {
                    base FORWARDING_RULE;
                    description    
                "LTPs referenced by the FD (or indirectly by the Link between FDs) MUST have FCs created between them.
                        This rule overrides all others except the CANNOT_FORWARD rule.";
                }
                identity FORWARDING_RULE_MAY_FORWARD_ACROSS_FD_LINK {
                    base FORWARDING_RULE;
                    description    
                "LTPs referenced by the FD (or indirectly by the Link between FDs) may have FCs created between them.
                        FCs may not be created between points that are not related by this rule either directly in an FD or indirectly via a Link linking two or more FDs.
                        For a Link points in an FD at one end of the Link can be connected to points in an FD at an other end of the Link.";
                }
                identity FORWARDING_RULE_NULL_FORWARDING_RULE {
                    base FORWARDING_RULE;
                    description    
                "none";
                }
                identity RULE_TYPE {
                    description    
                "none";
                }
                identity RULE_TYPE_FORWARDING {
                    base RULE_TYPE;
                    description    
                "The rule relates to creation of FCs.";
                }
                identity RULE_TYPE_COST {
                    base RULE_TYPE;
                    description    
                "The rule relates to forwarding cost.";
                }
                identity RULE_TYPE_RISK {
                    base RULE_TYPE;
                    description    
                "The rule relates to forwarding risk.";
                }
                identity RULE_TYPE_CAPACITY {
                    base RULE_TYPE;
                    description    
                "none";
                }
                identity PORT_ROLE_RULE_OPTION {
                    description    
                "none";
                }
                identity PORT_ROLE_RULE_OPTION_SAME_ROLE {
                    base PORT_ROLE_RULE_OPTION;
                    description    
                "The ports to which the rule applies must have role from the list in PortRole.";
                }
                identity PORT_ROLE_RULE_OPTION_DIFFERENT_ROLE {
                    base PORT_ROLE_RULE_OPTION;
                    description    
                "The ports to which the rule applies must not have a role from the list in PortRole.";
                }
                identity PORT_ROLE_RULE_OPTION_ANY_ROLE {
                    base PORT_ROLE_RULE_OPTION;
                    description    
                "The rule applies to any role of port.";
                }
                identity SIGNAL_PROPERTY_VALUE_RULE {
                    description    
                "none";
                }
                identity SIGNAL_PROPERTY_VALUE_RULE_SAME_VALUE {
                    base SIGNAL_PROPERTY_VALUE_RULE;
                    description    
                "none";
                }
                identity SIGNAL_PROPERTY_VALUE_RULE_ANY_VALUE {
                    base SIGNAL_PROPERTY_VALUE_RULE;
                    description    
                "none";
                }
                identity PARTNER {
                    description    
                "none";
                }
                identity PARTNER_FC {
                    base PARTNER;
                    description    
                "ForwardingConstruct.";
                }
                identity PARTNER_FD {
                    base PARTNER;
                    description    
                "ForwardingDomain.";
                }
                identity PARTNER_LINK {
                    base PARTNER;
                    description    
                "Link.";
                }
                identity PARTNER_CASC {
                    base PARTNER;
                    description    
                "ConfigurationAndSwitchController.";
                }
                identity PARTNER_CC {
                    base PARTNER;
                    description    
                "ControlConstruct.";
                }
                identity PARTNER_CD {
                    base PARTNER;
                    description    
                "ConstraintDomain.";
                }
                identity PARTNER_PC {
                    base PARTNER;
                    description    
                "ProcessingConstruct.";
                }
                identity PARTNER_PEER {
                    base PARTNER;
                    description    
                "LTP peer.";
                }
                identity PARTNER_CLIENT {
                    base PARTNER;
                    description    
                "LTP client.";
                }
                identity PARTNER_SERVER {
                    base PARTNER;
                    description    
                "LTP server.";
                }
                identity PARTNER_VIEW {
                    base PARTNER;
                    description    
                "LTP in other view.";
                }
                identity TASK_LIFECYCLE_STATE {
                    description    
                "none";
                }
                identity TASK_LIFECYCLE_STATE_RUNNING {
                    base TASK_LIFECYCLE_STATE;
                    description    
                "The task is running.";
                }
                identity TASK_LIFECYCLE_STATE_PAUSED {
                    base TASK_LIFECYCLE_STATE;
                    description    
                "The task has been paused.";
                }
                identity TASK_LIFECYCLE_STATE_WAITING {
                    base TASK_LIFECYCLE_STATE;
                    description    
                "The task is waiting for input etc.";
                }
                identity TASK_LIFECYCLE_STATE_ABORTING {
                    base TASK_LIFECYCLE_STATE;
                    description    
                "The task is aborting.";
                }
                identity TASK_LIFECYCLE_STATE_COMPLETED {
                    base TASK_LIFECYCLE_STATE;
                    description    
                "The task has been completed successfully.";
                }
                identity TASK_LIFECYCLE_STATE_ABORTED {
                    base TASK_LIFECYCLE_STATE;
                    description    
                "The task has been aborted.";
                }
                identity TASK_LIFECYCLE_STATE_ATTEMPTING_ROLLBACK {
                    base TASK_LIFECYCLE_STATE;
                    description    
                "The task is attempting to return the controlled system to a previous state.";
                }
                identity TASK_LIFECYCLE_STATE_ROLLBACK_COMPLETE {
                    base TASK_LIFECYCLE_STATE;
                    description    
                "The task has completed a roll back action.";
                }
                identity TASK_LIFECYCLE_STATE_ABANDONING {
                    base TASK_LIFECYCLE_STATE;
                    description    
                "Task is abandoning.";
                }
                identity TASK_LIFECYCLE_STATE_ABANDONED {
                    base TASK_LIFECYCLE_STATE;
                    description    
                "The task has been abandoned and is no longer running.";
                }
                identity TASK_LIFECYCLE_STATE_FAILED {
                    base TASK_LIFECYCLE_STATE;
                    description    
                "The task has failed.";
                }
                identity TASK_LIFECYCLE_STATE_ARCHIVED {
                    base TASK_LIFECYCLE_STATE;
                    description    
                "The task has been archived (and is no longer running).";
                }
                identity PROGRESS_STATUS {
                    description    
                "none";
                }
                identity PROGRESS_STATUS_COMPLETE {
                    base PROGRESS_STATUS;
                    description    
                "none";
                }
                identity PROGRESS_STATUS_IN_PROGRESS {
                    base PROGRESS_STATUS;
                    description    
                "none";
                }
                identity PROGRESS_STATUS_FAILED {
                    base PROGRESS_STATUS;
                    description    
                "none";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity.";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity.";
                }
                identity TERMINATION_DIRECTION_UNDEFINED_OR_UNKNOWN {
                    base TERMINATION_DIRECTION;
                    description    
                "Not a normal state. The system is unable to determine the correct value.";
                }
                identity TERMINATION_DIRECTION {
                    description    
                "none";
                }
                identity TERMINATION_DIRECTION_BIDIRECTIONAL {
                    base TERMINATION_DIRECTION;
                    description    
                "A Termination with both SINK and SOURCE flows.";
                }
                identity TERMINATION_DIRECTION_SINK {
                    base TERMINATION_DIRECTION;
                    description    
                "The flow is up the layer stack from the server side to the client side. 
                        Considering an example of a Termination function within the termination entity, a SINK flow:
                        - will arrive at the base of the termination function (the server side) where it is essentially at an INPUT to the termination component
                        - then will be decoded and deconstructed 
                        - then relevant parts of the flow will be sent out of the termination function (the client side) where it is essentially at an OUTPUT from the termination component
                        A SINK termination is one that only supports a SINK flow.
                        A SINK termination can be bound to an OUTPUT Port of a Forwarding entity";
                }
                identity TERMINATION_DIRECTION_SOURCE {
                    base TERMINATION_DIRECTION;
                    description    
                "The flow is down the layer stack from the server side to the client side. 
                        Considering an example of a Termination function within the termination entity, a SOURCE flow:
                        - will arrive at the top of the termination function (the client side) where it is essentially at an INPUT to the termination component
                        - then will be assembled with various overheads etc. and will be coded 
                        - then coded form of the assembly of flow will be sent out of the termination function (the server side) where it is essentially at an OUTPUT from the termination component
                        A SOURCE termination is one that only supports a SOURCE flow.
                        A SOURCE termination can be bound to an INPUT Port of a Forwarding entity";
                }
                identity TERMINATION_DIRECTION_UNDEFINED_OR_UNKNOWN {
                    base TERMINATION_DIRECTION;
                    description    
                "Not a normal state. The system is unable to determine the correct value.";
                }
                identity ACTION_VERBS {
                    description    
                "none";
                }
                identity ACTION_VERBS_CREATE_POST_ADD {
                    base ACTION_VERBS;
                    description    
                "none";
                }
                identity ACTION_VERBS_SET_UPDATE_PUT_MODIFY_WRITE_ADD {
                    base ACTION_VERBS;
                    description    
                "none";
                }
                identity ACTION_VERBS_GET_READ {
                    base ACTION_VERBS;
                    description    
                "none";
                }
                identity ACTION_VERBS_DELETE_REMOVE {
                    base ACTION_VERBS;
                    description    
                "none";
                }
                identity DIRECTION {
                    description    
                "none";
                }
                identity DIRECTION_IN {
                    base DIRECTION;
                    description    
                "none";
                }
                identity DIRECTION_OUT {
                    base DIRECTION;
                    description    
                "none";
                }
                identity DIRECTION_BIDIRECTIONAL {
                    base DIRECTION;
                    description    
                "none";
                }
                identity ACTION_VERBS {
                    description    
                "none";
                }
                identity ACTION_VERBS_CREATE_POST_ADD {
                    base ACTION_VERBS;
                    description    
                "Cause the addition of some structure.";
                }
                identity ACTION_VERBS_SET_UPDATE_PUT_MODIFY_WRITE_ADD {
                    base ACTION_VERBS;
                    description    
                "Cause the adjustment to some properties.";
                }
                identity ACTION_VERBS_GET_READ {
                    base ACTION_VERBS;
                    description    
                "Acquire information.";
                }
                identity ACTION_VERBS_DELETE_REMOVE {
                    base ACTION_VERBS;
                    description    
                "Eliminate some structure.";
                }
                identity ACTIVITY_DIRECTIVE {
                    description    
                "none";
                }
                identity ACTIVITY_DIRECTIVE_STRUCTURE_IS_NOT {
                    base ACTIVITY_DIRECTIVE;
                    description    
                "The structure defined should not be present. No part should be present (within the stated degrees of precision.";
                }
                identity ACTIVITY_DIRECTIVE_NEW_STRUCTURE_AND_VALUES {
                    base ACTIVITY_DIRECTIVE;
                    description    
                "None of the structure stated is expected to be present, but is required.";
                }
                identity ACTIVITY_DIRECTIVE_INCREMENTAL_STRUCTURE_AND_VALUES {
                    base ACTIVITY_DIRECTIVE;
                    description    
                "The structure stated is an increment on what already exists.
                        Increment in this case may also be decrement.";
                }
                identity ACTIVITY_DIRECTIVE_ONLY_VALUES_IN_EXISTING_STRUCTURE {
                    base ACTIVITY_DIRECTIVE;
                    description    
                "Only values should be modified, no new structure should be created and no structure should be deleted.";
                }
                identity ACTIVITY_DIRECTIVE_DEFINED_BY_VERB {
                    base ACTIVITY_DIRECTIVE;
                    description    
                "A verb is provided to give guidance (such as Create).";
                }
                identity ACTION_EFFORT {
                    description    
                "none";
                }
                identity ACTION_EFFORT_BEST_EFFORT {
                    base ACTION_EFFORT;
                    description    
                "none";
                }
                identity ACTION_EFFORT_EXACT_MATCH {
                    base ACTION_EFFORT;
                    description    
                "none";
                }
                identity PAUSE_RESUME_RULE {
                    description    
                "none";
                }
                identity PAUSE_RESUME_RULE_NO_PAUSE_POSSIBLE {
                    base PAUSE_RESUME_RULE;
                    description    
                "none";
                }
                grouping port-role-rule {
                    leaf-list port-role {
                        type port-role;
                        description     
                 "The role of the port considered.";
                    }
                    leaf-list port-role-rule {
                        type port-role-rule-option;
                        description     
                 "none";
                    }
                    description    
                "Constrains which ports the rule applies to.";
                }
                grouping signal-property-rule {
                    leaf signal-property-name {
                        type string;
                        description    
                    "The name of the signal property to which the rule applies.";
                    }
                    leaf signal-property-value-rule {
                        type signal-property-value-rule;
                        description    
                    "Indicates whether signal properties should be accounted for or not.";
                    }
                    leaf-list applicable-signal-value {
                        type string;
                        description     
                 "Specific values of the signal property to which the rule applies.";
                    }
                    description    
                "none";
                }


        /****************************************
        * package ltp-capability
        **************************************/ 
            /****************************************
            * grouping statements for object classes
            **************************************/ 
                grouping lp-spec {
                    list termination-spec {
                        uses termination-spec;
                        description    
                "A termination function of the LP.";
                    }
                    list adapter-property-spec {
                        uses adapter-property-spec;
                        description    
                "An adapter definition of the LP.";
                    }
                    container provider-view-spec {
                        uses provider-view-spec;
                        description    
                "Access to the resources made available from another view.";
                    }
                    list server-spec {
                        uses server-spec;
                        description    
                "Access to the resources from the provider.";
                    }
                    leaf-list lp-spec {
                        type leafref {
                            pathmust "/core-model:lp-spec/core-model:lp-spec/core-model:";
                    require-instance false;
                        }
                must  'deref(.) = current()';
                        description     
                 "Component LP of an LP.";
                    }
                    leaf spec-target-class {
                        type metaclass-class-name;
                        default "LayerProtocol";
                        description    
                    "The name of the class (e.g. LayerProtocol) to which the specification applies.";
                    }
                    list internal-forwarding-spec {
                        uses internal-forwarding-spec;
                        description    
                "Internal forwarding definition of the LP.";
                    }
                    list lp-port-spec {
                        uses lp-port-spec;
                        description    
                "Ports on the LP connecting to other LPs or to the ports of the LTP.";
                    }
                    description    
                "The specification of the capabilities of a specific type of LP.";
                }
                grouping client-spec {
                    list mapping-interaction-rule {
                        uses mapping-interaction-rule-spec;
                        description    
                "none";
                    }
                    description    
                "The specification of a client layer protocol supported by the adapter of an LP.";
                }
                grouping mapping-interaction-rule-spec {
                    description    
                "The specification of the interaction between the support for different client layer protocol signals.
                        For example an LP that supports 20 layer protocol X signals and 5 layer protocol Y signals may be such that a particular layer protocol X instance being used eliminates the possibility of using a particular layer protocol Y instance being used.";
                }
                grouping termination-spec {
                    container internal-forwarding-spec-port {
                        uses internal-forwarding-spec-port;
                        description    
                "none";
                    }
                    list adapter-property-spec {
                        uses adapter-property-spec;
                        description    
                "none";
                    }
                    list lp-spec-reference-class-ref {
                        if-feature spectargetclass:-terminationspec;
                        uses metaclass-class;
                        description    
                "Reference to the specific LpSpec class that defines the properties that augment the instance of TerminationSpec.";
                    }
                    description    
                "The specification of the layer protocol termination (including framing, modulation etc.).
                        For example, the specification of the function that takes a MAC frame and extracts the content (removing the MAC address in the process).";
                }
                grouping adapter-property-spec {
                    list pool-property-spec {
                        uses pool-property-spec;
                        description    
                "none";
                    }
                    list constraining-mapping-interaction-rule {
                        uses mapping-interaction-rule-spec;
                        description    
                "none";
                    }
                    list owned-mapping-interaction-rule {
                        uses mapping-interaction-rule-spec;
                        description    
                "none";
                    }
                    container termination-access-port {
                        uses termination-spec;
                        description    
                "The Termination bound to the Adapter.";
                    }
                    description    
                "The specification of the properties of the client side adapter of an LP.";
                }
                grouping pool-property-spec {
                    container client-spec {
                        uses client-spec;
                        description    
                "none";
                    }
                    leaf client-capacity {
                        type to-be-defined;
                        description    
                    "The size of the units of the pool.";
                    }
                    list adapter-property-spec {
                        uses adapter-property-spec;
                        description    
                "none";
                    }
                    description    
                "The specification for the properties of the pool of available instances of a particular client layer protocol.
                        This may cover numbering range, capacity, number of instances etc.";
                }
                grouping internal-forwarding-spec-port {
                    leaf internal-forwarding-spec-port {
                        type leafref {
                            pathmust "/core-model:lp-spec/core-model:lp-spec/core-model:internal-forwarding-spec/core-model:internal-forwarding-spec-port/core-model:";
                    require-instance false;
                        }
                must  'deref(.) = current()';
                        description    
                    "Allows for specification of complex connectivity between multiple terminations in a sophisticated LP.";
                    }
                    description    
                "The specification of the flexibility of the association between the ConnectionPoint and the Termination of the LP.
                        This is the port of the Internal Forwarding and is the equivalent to the FcPort.";
                }
                grouping connection-point-and-adapter-spec {
                    container internal-forwarding-spec-port {
                        uses internal-forwarding-spec-port;
                        description    
                "none";
                    }
                    container pool-property-spec {
                        uses pool-property-spec;
                        description    
                "The specification of the server facing connection point and the adapter that deals with the transformation of a single signal of the layer protocol to/from the server.
                            Equivalent to an ITU-T CTP [ITU-T G.8052].";
                    }
                    container server-access-point {
                        uses server-spec;
                        description    
                "none";
                    }
                    list lp-spec-reference-class-ref {
                        if-feature spectargetclass:-connectionpointandandapterspec;
                        uses metaclass-class;
                        description    
                "Reference to the specific LpSpec class that defines the properties that augment the instance of ConnectionPointAndAdapterSpec.";
                    }
                    description    
                "The specification of the server facing connection point and the adapter that deals with the transformation of a single signal of the layer protocol to/from the server.
                        Equivalent to an ITU-T CTP [ITU-T G.8052][G.874.1].";
                }
                grouping provider-view-spec {
                    list pool-property-spec {
                        uses pool-property-spec;
                        description    
                "none";
                    }
                    description    
                "The specification of the properties of an LP at the base of a virtual/floating LTP that relate to the provider of capacity/capability for that floating LTP.";
                }
                grouping server-spec {
                    description    
                "The specification of the server side of an LP at the base of an LTP that supports the creation of server LTPs for use in an inverse multiplexing scheme.";
                }
                grouping ltp-spec {
                    leaf-list lp-spec {
                        type leafref {
                            pathmust "/core-model:lp-spec/core-model:lp-spec/core-model:";
                    require-instance false;
                        }
                must  'deref(.) = current()';
                        min-elements 1;
                        description     
                 "none";
                    }
                    leaf spec-target-class {
                        type metaclass-class-name;
                        default "LogicalTerminationPoint";
                        description    
                    "The name of the class (e.g. LogicalTerminationPoint) to which the specification applies.";
                    }
                    list ltp-port-spec {
                        uses ltp-port-spec;
                        description    
                "none";
                    }
                    list lp-occurrence {
                        uses lp-occurrence;
                        description    
                "none";
                    }
                    description    
                "The specification of a specific type of LTP.";
                }
                grouping internal-forwarding-spec {
                    list internal-forwarding-spec-port {
                        uses internal-forwarding-spec-port;
                        description    
                "none";
                    }
                    list fc-spec-reference-class-ref {
                        min-elements 1;
                        uses metaclass-class;
                        description    
                "Reference to the specific FcSpec class that defines the properties that augment the instance of InternalForwardingSpec.";
                    }
                    description    
                "InternalForwardingSpec defines the encapsulated forwarding in the LP.
                        The InternalForwarding is essentially a ForwardingConstruct.";
                }
                grouping lp-port-spec {
                    leaf-list internal-forwarding-spec-port {
                        type leafref {
                            pathmust "/core-model:lp-spec/core-model:lp-spec/core-model:internal-forwarding-spec/core-model:internal-forwarding-spec-port/core-model:";
                    require-instance false;
                        }
                must  'deref(.) = current()';
                        description     
                 "none";
                    }
                    container termination-forwarding-port {
                        uses termination-spec;
                        description    
                "none";
                    }
                    container cp-forwarding-port {
                        uses connection-point-and-adapter-spec;
                        description    
                "none";
                    }
                    container provider-view {
                        uses provider-view-spec;
                        description    
                "none";
                    }
                    container pool-property-spec-client-access {
                        uses pool-property-spec;
                        description    
                "none";
                    }
                    container termination-access-port {
                        uses termination-spec;
                        description    
                "none";
                    }
                    container adapter-provider-access {
                        uses adapter-property-spec;
                        description    
                "none";
                    }
                    container provider-access {
                        uses server-spec;
                        description    
                "none";
                    }
                    description    
                "The spec for the ports of the LP.";
                }
                grouping lp-occurrence {
                    list lp-port-occurrence {
                        min-elements 1;
                        uses lp-port-occurrence;
                        description    
                "none";
                    }
                    container lp-spec {
                        uses lp-spec;
                        description    
                "none";
                    }
                    description    
                "An occurrence of a LP in the specified LTP where the LP occurrence will have an identifier.
                        The LP occurrence will have a spec.";
                }
                grouping lp-port-occurrence {
                    container lp-port-spec {
                        uses lp-port-spec;
                        description    
                "none";
                    }
                    leaf bound-to-lp-port-occurrence {
                        type leafref {
                            pathmust "/core-model:ltp-spec/core-model:lp-occurrence/core-model:lp-port-occurrence/core-model:";
                    require-instance false;
                        }
                must  'deref(.) = current()';
                        description    
                    "none";
                    }
                    description    
                "The occurrence of a port on the LP occurrence.
                        The port occurrence will correspond to a port in the spec of the corresponding LpOccurrence.";
                }
                grouping ltp-port-spec {
                    container lp-port-occurrence {
                        uses lp-port-occurrence;
                        description    
                "none";
                    }
                    list external-access {
                        uses access-opportuity;
                        description    
                "none";
                    }
                    description    
                "Spec for the LTP Port. Each LTP Port relates to an association end related to the LTP class.";
                }
                grouping layer-protocol-parameter-spec {
                    description    
                "Offers the opportunity to define a list of layer-protocol related parameters. 
                        Used to specify the extension a class. ";
                }
                feature spectargetclass:-terminationspec {
                description    
                none;
                }
                feature spectargetclass:-connectionpointandandapterspec {
                description    
                none;
                }

            /****************************************
            * package type-definition
            **************************************/ 
                grouping access-opportuity {
                    leaf partner {
                        type partner;
                        description    
                    "The class of the instance to which this port may be bound.";
                    }
                    leaf qualifier {
                        type string;
                        description    
                    "A property of the instance of the related class that must be present at a stated value to allow the ports to be bound.
                            For example the layerProtocol of a related port must be of the same as the layerProtocol of LP related to the LTP port.
                            This attribute requires more formal definition.";
                    }
                    description    
                "none";
                }
                typedef partner {
                    type identityref {
                        base PARTNER;
                    }
                    description    
                "The class of the instance to which this port may be related.";
                }


/****************************************
* typedef statements
**************************************/ 
            typedef metaclass-class-name {
                type string;
                description    
                "none";
            }

/*********************************************
* grouping statements for complex data types
*******************************************/ 
            identity PORT_DIRECTION {
                description    
                "none";
            }
            identity PORT_DIRECTION_BIDIRECTIONAL {
                base PORT_DIRECTION;
                description    
                "The Port has both an INPUT flow and an OUTPUT flow defined.";
            }
            identity PORT_DIRECTION_INPUT {
                base PORT_DIRECTION;
                description    
                "The Port only has definition for a flow into the Forwarding entity (i.e. an ingress flow).";
            }
            identity PORT_DIRECTION_OUTPUT {
                base PORT_DIRECTION;
                description    
                "The Port only has definition for a flow out of the Forwarding entity (i.e. an egress flow).";
            }
            identity PORT_DIRECTION_UNIDENTIFIED_OR_UNKNOWN {
                base PORT_DIRECTION;
                description    
                "Not a normal state. The system is unable to determine the correct value.";
            }
            identity PORT_DIRECTION_OMNIDIRECTIONAL {
                base PORT_DIRECTION;
                description    
                "none";
            }
            identity FORWARDING_DIRECTION {
                description    
                "none";
            }
            identity FORWARDING_DIRECTION_BIDIRECTIONAL {
                base FORWARDING_DIRECTION;
                description    
                "The Forwarding entity supports both BIDIRECTIONAL flows at all Ports (i.e. all Ports have both an INPUT flow and an OUTPUT flow defined).";
            }
            identity FORWARDING_DIRECTION_UNIDIRECTIONAL {
                base FORWARDING_DIRECTION;
                description    
                "The Forwarding entity has Ports that are either INPUT or OUTPUT. It has no BIDIRECTIONAL Ports.";
            }
            identity FORWARDING_DIRECTION_UNDEFINED_OR_UNKNOWN {
                base FORWARDING_DIRECTION;
                description    
                "Not a normal state. The system is unable to determine the correct value.";
            }
            identity FORWARDING_DIRECTION_OMNIDIRECTIONAL {
                base FORWARDING_DIRECTION;
                description    
                "none";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base TERMINATION_DIRECTION;
                description    
                "Not a normal state. The system is unable to determine the correct value.";
            }
            identity EXTENDED_TERMINATION_DIRECTION {
                description    
                "none";
            }
            identity EXTENDED_TERMINATION_DIRECTION_CONTRA_DIRECTION_SINK {
                base EXTENDED_TERMINATION_DIRECTION;
                description    
                "The essential flow of the Termination entity is SINK (i.e. up the layer stack) but the INPUT flow of the Termination entity was provided by a SOURCE OUTPUT or taken from a SOURCE INPUT (duplicating the input signal) hence reversing the flow orientation from down the layer stack to up the layer stack.";
            }
            identity EXTENDED_TERMINATION_DIRECTION_CONTRA_DIRECTION_SOURCE {
                base EXTENDED_TERMINATION_DIRECTION;
                description    
                "The essential flow of the Termination entity is SOURCE (i.e. down the layer stack) but the OUTPUT flow of the Termination entity was fed to (and replaces) a SINK OUTPUT or was fed to a SINK INPUT (replacing the normal flow) hence reversing the flow orientation from down the layer stack to up the layer stack.";
            }
            identity TERMINATION_STATE {
                description    
                "none";
            }
            identity TERMINATION_STATE_LP_CAN_NEVER_TERMINATE {
                base TERMINATION_STATE;
                description    
                "A non-flexible case that can never be terminated.";
            }
            identity TERMINATION_STATE_LP_NOT_TERMINATED {
                base TERMINATION_STATE;
                description    
                "A flexible termination that can terminate but is currently not terminated.";
            }
            identity TERMINATION_STATE_TERMINATED_SERVER_TO_CLIENT_FLOW {
                base TERMINATION_STATE;
                description    
                "A flexible termination that is currently terminated for server to client flow only.";
            }
            identity TERMINATION_STATE_TERMINATED_CLIENT_TO_SERVER_FLOW {
                base TERMINATION_STATE;
                description    
                "A flexible termination that is currently terminated for client to server flow only.";
            }
            identity TERMINATION_STATE_TERMINATED_BIDIRECTIONAL {
                base TERMINATION_STATE;
                description    
                "A flexible termination that is currently terminated in both directions of flow.";
            }
            identity TERMINATION_STATE_LP_PERMENANTLY_TERMINATED {
                base TERMINATION_STATE;
                description    
                "A non-flexible termination that is always terminated (in both directions of flow for a bidirectional case and in the one direction of flow for both unidirectional cases).";
            }
            identity TERMINATION_STATE_TERMINATION_STATE_UNKNOWN {
                base TERMINATION_STATE;
                description    
                "There TerminationState cannot be determined.";
            }
            identity PROTECTION_REASON {
                description    
                "none";
            }
            identity PROTECTION_REASON_WAIT_TO_REVERT {
                base PROTECTION_REASON;
                description    
                "The resource is selected as control is waiting to restore to a preferred resource.";
            }
            identity PROTECTION_REASON_SIGNAL_DEGRADE {
                base PROTECTION_REASON;
                description    
                "The resource is selected as the best preferred resource is in signal degrade.";
            }
            identity PROTECTION_REASON_SIGNAL_FAIL {
                base PROTECTION_REASON;
                description    
                "The resource is selected as the best preferred resource is in signal fail.";
            }
            identity ROUTE_SELECTION_CONTROL {
                description    
                "none";
            }
            identity ROUTE_SELECTION_CONTROL_LOCK_OUT {
                base ROUTE_SELECTION_CONTROL;
                description    
                "The resource is configured to temporarily not be available for use in the protection scheme(s) it is part of.
                    This overrides all other protection control states including forced.
                    If the item is locked out, then it cannot be used under any circumstances.
                    Note: Only relevant when part of a protection scheme.
                    Note: if a protection process that has a relationship to the item (i.e. is one of the options the protection process may choose) is deactivated by being isFrozen = true) then the lockout request will be rejected. ";
            }
            identity ROUTE_SELECTION_REASON {
                description    
                "none";
            }
            identity SWITCH_CONTROL {
                description    
                "none";
            }
            identity SWITCH_CONTROL_NORMAL {
                base SWITCH_CONTROL;
                description    
                "No administrative control applied to the switch.";
            }
            identity SWITCH_CONTROL_MANUAL {
                base SWITCH_CONTROL;
                description    
                "Resource temporarily chosen by control configuration where the resource is not the preferred resource.
                    Preferred resource has highest priority.
                    Temporarily overrides reversion.
                    If this resource fails, it will switch to best available resource. 
                    If resource selected is shared and another FC requires the resource, then the selection control will change to Normal and switch to best available based upon normal rules.
                    Cannot manually switch a Forced switch, cannot remove a forced switch, cannot switch to a locked out item and will be rejected if the protection process is deactivated by being Freeze = true).
                    A manual switch/route that is selecting an FcPort, LTP, FC, Link or Route that is subsequently set to LOCK_OUT will have the manual removed (changed to NORMAL) and will switch away from the FcPort with LOCK_OUT to best available based upon normal rules.
                    A manual switch that is selecting an FcPort that is subsequently selected by a Forced switch will be restored to normal operation and the manual will be removed.
                    A manual switch/route that is selecting an FcPort, LTP, FC, Link or Route that is subsequently manual selected by another switch/route will have the manual removed and will switch away from the FcPort.
                    Can be returned to NORMAL by configuration action.";
            }
            identity SWITCH_CONTROL_FORCED {
                base SWITCH_CONTROL;
                description    
                "Resource temporarily chosen by control configuration where the resource is not the preferred resource.
                    Preferred resource has highest priority.
                    Temporarily overrides reversion.
                    If this resource fails it will NOT switch. 
                    If resource selected is shared and another FC requires the resource through a FORCE on that FC and the FC is of a higher FcPriority then the selection control on this FC will change to NORMAL and switch to best available based upon normal rules.
                    If the resource selected is then set to LOCK_OUT then the selection control will change to NORMAL and switch to best available based upon normal rules.
                    Can be returned to NORMAL by configuration action.";
            }
            identity SWITCH_STATE_REASON {
                description    
                "none";
            }
            identity REVERSION_MODE {
                description    
                "none";
            }
            identity REVERSION_MODE_REVERTIVE {
                base REVERSION_MODE;
                description    
                "An FC switched to a lower priority (non-preferred) resource will revert to a higher priority (preferred) resource when that recovers (potentially after some hold-off time).";
            }
            identity REVERSION_MODE_NON-REVERTIVE {
                base REVERSION_MODE;
                description    
                "An FC switched to a lower priority (non-preferred) resource will not revert to a higher priority (preferred) resource when that recovers.";
            }
            identity RESILIENCE_CONTROL {
                description    
                "none";
            }
            identity RESILIENCE_CONTROL_QUIESCENT {
                base RESILIENCE_CONTROL;
                description    
                "none";
            }
            identity RESILIENCE_CONTROL_RESTORING {
                base RESILIENCE_CONTROL;
                description    
                "none";
            }
            identity RESILIENCE_CONTROL_RECOVERY_FAILED {
                base RESILIENCE_CONTROL;
                description    
                "none";
            }
            identity RESILIENCE_CONTROL_UNKNOWN {
                base RESILIENCE_CONTROL;
                description    
                "none";
            }
            identity RUN_MODE {
                description    
                "none";
            }
            identity RUN_MODE_FREE_RUN {
                base RUN_MODE;
                description    
                "The clock is not synchronized to another clock.";
            }
            identity RUN_MODE_LOCKED {
                base RUN_MODE;
                description    
                "The clock is synchronized to another clock.";
            }
            identity RUN_MODE_HOLD_OVER {
                base RUN_MODE;
                description    
                "The clock was previously synchronized to another clock but that timing input has been lost.
                    The clock is set to the last known synchronization.";
            }
            identity LAYER_PROTOCOL_NAME {
                description    
                "none";
            }
            identity LAYER_PROTOCOL_NAME_PHOTONIC_MEDIA {
                base LAYER_PROTOCOL_NAME;
                description    
                "The characteristic information is that of a channel able to carry photons and of the photon source/sink.";
            }
            identity LAYER_PROTOCOL_NAME_OTU_AND_ODU {
                base LAYER_PROTOCOL_NAME;
                description    
                "The characteristic information is that of a channel able to carry ODU/OTU protocol (OTN) and of the ODU/OTU source/sink.";
            }
            identity LAYER_PROTOCOL_NAME_ETHERNET {
                base LAYER_PROTOCOL_NAME;
                description    
                "The characteristic information is that of a channel able to carry Ethernet protocol and of the Ethernet protocol source/sink.";
            }
            identity OPERATIONAL_STATE {
                description    
                "none";
            }
            identity OPERATIONAL_STATE_DISABLED {
                base OPERATIONAL_STATE;
                description    
                "The resource is unable to meet the SLA of the user of the resource. 
                    If no (explicit) SLA is defined the resource is disabled if it is totally inoperable and unable to provide service to the user.";
            }
            identity OPERATIONAL_STATE_ENABLED {
                base OPERATIONAL_STATE;
                description    
                "The resource is partially or fully operable and available for use.";
            }
            identity ADMINISTRATIVE_STATE {
                description    
                "none";
            }
            identity ADMINISTRATIVE_STATE_LOCKED {
                base ADMINISTRATIVE_STATE;
                description    
                "Users are administratively prohibited from making use of the resource.";
            }
            identity ADMINISTRATIVE_STATE_UNLOCKED {
                base ADMINISTRATIVE_STATE;
                description    
                "Users are allowed to use the resource.";
            }
            identity ADMINISTRATIVE_STATE_SHUTTING_DOWN {
                base ADMINISTRATIVE_STATE;
                description    
                "The entity is administratively restricted to existing instances of use only. There may be specific actions to remove existing uses. No new instances of use can be enabled.
                    The resource automatically transitions to “locked” when the last user quits. 
                    The administrative state is not visible in the client context. 
                    The lifecycle state “pending removal” should be used to indicate to the client that the provider intends to remove the resource.";
            }
            identity ADMINISTRATIVE_CONTROL {
                description    
                "none";
            }
            identity ADMINISTRATIVE_CONTROL_UNLOCK {
                base ADMINISTRATIVE_CONTROL;
                description    
                "The intention is for the entity to become unlocked.
                    The entity may already be UNLOCKED.";
            }
            identity ADMINISTRATIVE_CONTROL_LOCK_PASSIVE {
                base ADMINISTRATIVE_CONTROL;
                description    
                "The intention is for the entity to become locked but no effort is expected to move to the Locked state (the state will be achieved once all users stop using the resource). 
                    The entity may be LOCKED.";
            }
            identity ADMINISTRATIVE_CONTROL_LOCK_ACTIVE {
                base ADMINISTRATIVE_CONTROL;
                description    
                "The intention is for the entity to become locked and it is expected that effort will be made to move to the Locked state (users will be actively removed). 
                    The entity may already be LOCKED.";
            }
            identity ADMINISTRATIVE_CONTROL_LOCK_IMMEDIATE {
                base ADMINISTRATIVE_CONTROL;
                description    
                "The intention is for the entity to become locked and it is expected to move to the Locked state immediately (users will be force removed). 
                    The entity may already be LOCKED.";
            }
            identity ADMINISTRATIVE_CONTROL_QUIESCENT {
                base ADMINISTRATIVE_CONTROL;
                description    
                "The administrative state is at a stable value (LOCKED/UNLOCKED) and no action is being taken.";
            }
            identity LIFECYCLE_STATE {
                description    
                "none";
            }
            identity LIFECYCLE_STATE_PLANNED {
                base LIFECYCLE_STATE;
                description    
                "The resource is planned but is not present in the network.
                    Should include a 'time' when the resources are expected to be installed.";
            }
            identity LIFECYCLE_STATE_POTENTIAL_AVAILABLE {
                base LIFECYCLE_STATE;
                description    
                "The supporting resources are present in the network but are shared with other clients; or require further configuration before they can be used; or both.
                    (1) When a potential resource is configured and allocated to a client it is moved to the INSTALLED state for that client.
                    (2) If the potential resource has been consumed (e.g. allocated to another client) it is moved to the POTENTIAL BUSY state for all other clients.";
            }
            identity LIFECYCLE_STATE_POTENTIAL_BUSY {
                base LIFECYCLE_STATE;
                description    
                "The supporting resources are present in the network but have been allocated to other clients.";
            }
            identity LIFECYCLE_STATE_INSTALLED {
                base LIFECYCLE_STATE;
                description    
                "The resource is present in the network and is capable of providing the service.";
            }
            identity LIFECYCLE_STATE_PENDING_REMOVAL {
                base LIFECYCLE_STATE;
                description    
                "The resource has been marked for removal. Should include a “time” when the resources are expected to be removed.";
            }
            identity BLOCK_DIRECTION {
                description    
                "none";
            }
            identity BLOCK_DIRECTION_NO_BLOCK {
                base BLOCK_DIRECTION;
                description    
                "The FC is not blocking signal related to the LTP.";
            }
            identity BLOCK_DIRECTION_INGRESS_BLOCK {
                base BLOCK_DIRECTION;
                description    
                "The FC is blocking signal that is flowing into the LTP from the FC.";
            }
            identity BLOCK_DIRECTION_EGRESS_BLOCK {
                base BLOCK_DIRECTION;
                description    
                "The FC is blocking signal flowing out of the LTP to the FC.";
            }
            identity BLOCK_DIRECTION_BIDIRECTIONAL_BLOCK {
                base BLOCK_DIRECTION;
                description    
                "The FC is blocking both directions of traffic, i.e. Ingress and Egress, to/from the LTP.";
            }
            identity CONNECTOR_AND_PIN_ORIENTATION {
                description    
                "none";
            }
            identity CONNECTOR_AND_PIN_ORIENTATION_MALE {
                base CONNECTOR_AND_PIN_ORIENTATION;
                description    
                "The connecting elements are dominantly protrusions.";
            }
            identity CONNECTOR_AND_PIN_ORIENTATION_FEMALE {
                base CONNECTOR_AND_PIN_ORIENTATION;
                description    
                "The connecting elements are dominantly indentations.";
            }
            identity CONNECTOR_AND_PIN_ORIENTATION_SYMMETRIC_NEUTRAL {
                base CONNECTOR_AND_PIN_ORIENTATION;
                description    
                "The pin (and housing) orientation combination is such that it is symmetric so a connector is compatible with itself.
                    The connecting element may be a surface rather than protrusions or indentations.";
            }
            identity EQUIPMENT_CATEGORY {
                description    
                "none";
            }
            identity EQUIPMENT_CATEGORY_SUBRACK {
                base EQUIPMENT_CATEGORY;
                description    
                "An assembly with holders designed to accommodate CIRCUIT_PACKs. 
                    The assembly is designed to be mounted in a RACK.";
            }
            identity EQUIPMENT_CATEGORY_CIRCUIT_PACK {
                base EQUIPMENT_CATEGORY;
                description    
                "An assembly with connectors compatible with those in a holder.
                    The assembly is designed to be mounted in a holder (SLOT) of a SUBRACK.
                    May also support holders (SLOTs) for SMALL_FORMFACTOR_PLUGGABLEs.";
            }
            identity EQUIPMENT_CATEGORY_SMALL_FORMFACTOR_PLUGGABLE {
                base EQUIPMENT_CATEGORY;
                description    
                "A small assembly (compared to a CIRCUIT_PACK) with connectors compatible with those in a holder.
                    The assembly is designed to be mounted in a holder (SLOT) of a CIRCUIT_PACK or STAND_ALONE_UNIT.";
            }
            identity EQUIPMENT_CATEGORY_STAND_ALONE_UNIT {
                base EQUIPMENT_CATEGORY;
                description    
                "An assembly with connectors for cabling and potentially with holders.
                    The assembly is designed to be mounted in a freeform environment (on a table or simple mechanical cabinet).
                    May support holders (SLOTs) for CIRCUIT_PACKs or for SMALL_FORMFACTOR_PLUGGABLEs.";
            }
            identity EQUIPMENT_CATEGORY_RACK {
                base EQUIPMENT_CATEGORY;
                description    
                "A mechanical assembly with cabling and predefined mounting points for particular SUBRACK types.
                    The assembly is designed to be mounted on the floor in a row with other RACKs.";
            }
            identity HOLDER_CATEGORY {
                description    
                "none";
            }
            identity HOLDER_CATEGORY_SLOT {
                base HOLDER_CATEGORY;
                description    
                "A guided holder with fixed connectors.
                    The guided holder is designed to take a particular form of CIRCUIT_PACK or SMALL_FORMFACTOR_PLUGGABLE";
            }
            identity FORWARDING_RULE {
                description    
                "none";
            }
            identity FORWARDING_RULE_CANNOT_FORWARD_ACROSS_FD_LINK {
                base FORWARDING_RULE;
                description    
                "LTPs referenced by the FD (or indirectly by the Link between FDs) cannot have FCs created between them.
                    This rule overrides all others.";
            }
            identity FORWARDING_RULE_MUST_FORWARD_ACROSS_FD_LINK {
                base FORWARDING_RULE;
                description    
                "LTPs referenced by the FD (or indirectly by the Link between FDs) MUST have FCs created between them.
                    This rule overrides all others except the CANNOT_FORWARD rule.";
            }
            identity FORWARDING_RULE_MAY_FORWARD_ACROSS_FD_LINK {
                base FORWARDING_RULE;
                description    
                "LTPs referenced by the FD (or indirectly by the Link between FDs) may have FCs created between them.
                    FCs may not be created between points that are not related by this rule either directly in an FD or indirectly via a Link linking two or more FDs.
                    For a Link points in an FD at one end of the Link can be connected to points in an FD at an other end of the Link.";
            }
            identity FORWARDING_RULE_NULL_FORWARDING_RULE {
                base FORWARDING_RULE;
                description    
                "none";
            }
            identity RULE_TYPE {
                description    
                "none";
            }
            identity RULE_TYPE_FORWARDING {
                base RULE_TYPE;
                description    
                "The rule relates to creation of FCs.";
            }
            identity RULE_TYPE_COST {
                base RULE_TYPE;
                description    
                "The rule relates to forwarding cost.";
            }
            identity RULE_TYPE_RISK {
                base RULE_TYPE;
                description    
                "The rule relates to forwarding risk.";
            }
            identity RULE_TYPE_CAPACITY {
                base RULE_TYPE;
                description    
                "none";
            }
            identity PORT_ROLE_RULE_OPTION {
                description    
                "none";
            }
            identity PORT_ROLE_RULE_OPTION_SAME_ROLE {
                base PORT_ROLE_RULE_OPTION;
                description    
                "The ports to which the rule applies must have role from the list in PortRole.";
            }
            identity PORT_ROLE_RULE_OPTION_DIFFERENT_ROLE {
                base PORT_ROLE_RULE_OPTION;
                description    
                "The ports to which the rule applies must not have a role from the list in PortRole.";
            }
            identity PORT_ROLE_RULE_OPTION_ANY_ROLE {
                base PORT_ROLE_RULE_OPTION;
                description    
                "The rule applies to any role of port.";
            }
            identity SIGNAL_PROPERTY_VALUE_RULE {
                description    
                "none";
            }
            identity SIGNAL_PROPERTY_VALUE_RULE_SAME_VALUE {
                base SIGNAL_PROPERTY_VALUE_RULE;
                description    
                "none";
            }
            identity SIGNAL_PROPERTY_VALUE_RULE_ANY_VALUE {
                base SIGNAL_PROPERTY_VALUE_RULE;
                description    
                "none";
            }
            identity PARTNER {
                description    
                "none";
            }
            identity PARTNER_FC {
                base PARTNER;
                description    
                "ForwardingConstruct.";
            }
            identity PARTNER_FD {
                base PARTNER;
                description    
                "ForwardingDomain.";
            }
            identity PARTNER_LINK {
                base PARTNER;
                description    
                "Link.";
            }
            identity PARTNER_CASC {
                base PARTNER;
                description    
                "ConfigurationAndSwitchController.";
            }
            identity PARTNER_CC {
                base PARTNER;
                description    
                "ControlConstruct.";
            }
            identity PARTNER_CD {
                base PARTNER;
                description    
                "ConstraintDomain.";
            }
            identity PARTNER_PC {
                base PARTNER;
                description    
                "ProcessingConstruct.";
            }
            identity PARTNER_PEER {
                base PARTNER;
                description    
                "LTP peer.";
            }
            identity PARTNER_CLIENT {
                base PARTNER;
                description    
                "LTP client.";
            }
            identity PARTNER_SERVER {
                base PARTNER;
                description    
                "LTP server.";
            }
            identity PARTNER_VIEW {
                base PARTNER;
                description    
                "LTP in other view.";
            }
            identity TASK_LIFECYCLE_STATE {
                description    
                "none";
            }
            identity TASK_LIFECYCLE_STATE_RUNNING {
                base TASK_LIFECYCLE_STATE;
                description    
                "The task is running.";
            }
            identity TASK_LIFECYCLE_STATE_PAUSED {
                base TASK_LIFECYCLE_STATE;
                description    
                "The task has been paused.";
            }
            identity TASK_LIFECYCLE_STATE_WAITING {
                base TASK_LIFECYCLE_STATE;
                description    
                "The task is waiting for input etc.";
            }
            identity TASK_LIFECYCLE_STATE_ABORTING {
                base TASK_LIFECYCLE_STATE;
                description    
                "The task is aborting.";
            }
            identity TASK_LIFECYCLE_STATE_COMPLETED {
                base TASK_LIFECYCLE_STATE;
                description    
                "The task has been completed successfully.";
            }
            identity TASK_LIFECYCLE_STATE_ABORTED {
                base TASK_LIFECYCLE_STATE;
                description    
                "The task has been aborted.";
            }
            identity TASK_LIFECYCLE_STATE_ATTEMPTING_ROLLBACK {
                base TASK_LIFECYCLE_STATE;
                description    
                "The task is attempting to return the controlled system to a previous state.";
            }
            identity TASK_LIFECYCLE_STATE_ROLLBACK_COMPLETE {
                base TASK_LIFECYCLE_STATE;
                description    
                "The task has completed a roll back action.";
            }
            identity TASK_LIFECYCLE_STATE_ABANDONING {
                base TASK_LIFECYCLE_STATE;
                description    
                "Task is abandoning.";
            }
            identity TASK_LIFECYCLE_STATE_ABANDONED {
                base TASK_LIFECYCLE_STATE;
                description    
                "The task has been abandoned and is no longer running.";
            }
            identity TASK_LIFECYCLE_STATE_FAILED {
                base TASK_LIFECYCLE_STATE;
                description    
                "The task has failed.";
            }
            identity TASK_LIFECYCLE_STATE_ARCHIVED {
                base TASK_LIFECYCLE_STATE;
                description    
                "The task has been archived (and is no longer running).";
            }
            identity PROGRESS_STATUS {
                description    
                "none";
            }
            identity PROGRESS_STATUS_COMPLETE {
                base PROGRESS_STATUS;
                description    
                "none";
            }
            identity PROGRESS_STATUS_IN_PROGRESS {
                base PROGRESS_STATUS;
                description    
                "none";
            }
            identity PROGRESS_STATUS_FAILED {
                base PROGRESS_STATUS;
                description    
                "none";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity.";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity.";
            }
            identity TERMINATION_DIRECTION_UNDEFINED_OR_UNKNOWN {
                base TERMINATION_DIRECTION;
                description    
                "Not a normal state. The system is unable to determine the correct value.";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base TERMINATION_DIRECTION;
                description    
                "Not a normal state. The system is unable to determine the correct value.";
            }
            identity ACTION_VERBS {
                description    
                "none";
            }
            identity ACTION_VERBS_CREATE_POST_ADD {
                base ACTION_VERBS;
                description    
                "none";
            }
            identity ACTION_VERBS_SET_UPDATE_PUT_MODIFY_WRITE_ADD {
                base ACTION_VERBS;
                description    
                "none";
            }
            identity ACTION_VERBS_GET_READ {
                base ACTION_VERBS;
                description    
                "none";
            }
            identity ACTION_VERBS_DELETE_REMOVE {
                base ACTION_VERBS;
                description    
                "none";
            }
            identity DIRECTION {
                description    
                "none";
            }
            identity DIRECTION_IN {
                base DIRECTION;
                description    
                "none";
            }
            identity DIRECTION_OUT {
                base DIRECTION;
                description    
                "none";
            }
            identity DIRECTION_BIDIRECTIONAL {
                base DIRECTION;
                description    
                "none";
            }
            identity ACTION_VERBS {
                description    
                "none";
            }
            identity ACTION_VERBS_CREATE_POST_ADD {
                base ACTION_VERBS;
                description    
                "Cause the addition of some structure.";
            }
            identity ACTION_VERBS_SET_UPDATE_PUT_MODIFY_WRITE_ADD {
                base ACTION_VERBS;
                description    
                "Cause the adjustment to some properties.";
            }
            identity ACTION_VERBS_GET_READ {
                base ACTION_VERBS;
                description    
                "Acquire information.";
            }
            identity ACTION_VERBS_DELETE_REMOVE {
                base ACTION_VERBS;
                description    
                "Eliminate some structure.";
            }
            identity ACTIVITY_DIRECTIVE {
                description    
                "none";
            }
            identity ACTIVITY_DIRECTIVE_STRUCTURE_IS_NOT {
                base ACTIVITY_DIRECTIVE;
                description    
                "The structure defined should not be present. No part should be present (within the stated degrees of precision.";
            }
            identity ACTIVITY_DIRECTIVE_NEW_STRUCTURE_AND_VALUES {
                base ACTIVITY_DIRECTIVE;
                description    
                "None of the structure stated is expected to be present, but is required.";
            }
            identity ACTIVITY_DIRECTIVE_INCREMENTAL_STRUCTURE_AND_VALUES {
                base ACTIVITY_DIRECTIVE;
                description    
                "The structure stated is an increment on what already exists.
                    Increment in this case may also be decrement.";
            }
            identity ACTIVITY_DIRECTIVE_ONLY_VALUES_IN_EXISTING_STRUCTURE {
                base ACTIVITY_DIRECTIVE;
                description    
                "Only values should be modified, no new structure should be created and no structure should be deleted.";
            }
            identity ACTIVITY_DIRECTIVE_DEFINED_BY_VERB {
                base ACTIVITY_DIRECTIVE;
                description    
                "A verb is provided to give guidance (such as Create).";
            }
            identity ACTION_EFFORT {
                description    
                "none";
            }
            identity ACTION_EFFORT_BEST_EFFORT {
                base ACTION_EFFORT;
                description    
                "none";
            }
            identity ACTION_EFFORT_EXACT_MATCH {
                base ACTION_EFFORT;
                description    
                "none";
            }
            identity PAUSE_RESUME_RULE {
                description    
                "none";
            }
            identity PAUSE_RESUME_RULE_NO_PAUSE_POSSIBLE {
                base PAUSE_RESUME_RULE;
                description    
                "none";
            }
            grouping metaclass-class {
                leaf name {
                    type metaclass-class-name;
                    description    
                    "The text name of the Class";
                }
                description    
                "This datatype represents the '<<Metaclass>> Class' from the UML metamodel. 
                    An instance of the referencing Class (e.g. LTP) will reference a Class (not an instance).
                    This referenced Class will provide definition to extend the referencing instance. 
                    So, for example, an LTP instance will have the attributes defined in the LTP class and also the attributes defined in the referenced Class (an LtpSpec).
                    The referenced Class may:
                    (1) provide invariant properties (that are the same for many instances) that then are not conveyed with the referencing instance.
                    (2) provide definitions for attributes that are present in the instance that are not defined in the Class of the instance (these attribute may have been pruned and refactored from one or more external definition sources). 
                    (3) apply constraints to attributes in the instance that were defined in the class of the referencing instance.
                    (4) replace attributes that were present in the class of the referencing instance by a new definition (same name).;
";
            }

        /****************************************
        * package spec-pattern
        **************************************/ 
            /****************************************
            * grouping statements for object classes
            **************************************/ 
                grouping composed-part {
                    list part-spec-reference-class-ref {
                        if-feature spectargetclass-entity/composedpart;
                        min-elements 1;
                        uses metaclass-class;
                        description    
                "none";
                    }
                    description    
                "none";
                }
                grouping entity {
                    list extension-container {
                        uses extension-container;
                        description    
                "none";
                    }
                    list composed-part {
                        uses composed-part;
                        description    
                "none";
                    }
                    list entity-spec-reference-class-ref {
                        if-feature spectargetclass-entity;
                        min-elements 1;
                        uses metaclass-class;
                        description    
                "none";
                    }
                    description    
                "none";
                }
                grouping entity-spec {
                    list part-spec {
                        uses part-spec;
                        description    
                "none";
                    }
                    leaf spec-target-class {
                        type metaclass-class-name;
                        description    
                    "The name of the class (e.g. ForwardingConstruct) to which the specification applies.";
                    }
                    description    
                "none";
                }
                grouping extension-container {
                    list entity-spec-reference-class-ref {
                        if-feature spectargetclass-entity/extensioncontainer;
                        min-elements 1;
                        uses metaclass-class;
                        description    
                "none";
                    }
                    description    
                "none";
                }
                grouping part-spec {
                    leaf spec-target-class {
                        type metaclass-class-name;
                        description    
                    "The name of the class (e.g. LayerProtocol) to which the specification applies.";
                    }
                    description    
                "none";
                }
                feature spectargetclass-entity/composedpart {
                description    
                none;
                }
                feature spectargetclass-entity {
                description    
                none;
                }
                feature spectargetclass-entity/extensioncontainer {
                description    
                none;
                }


        /****************************************
        * package clock-spec
        **************************************/ 
            /****************************************
            * grouping statements for object classes
            **************************************/ 
                grouping clock-spec {
                    leaf-list clock-spec {
                        type leafref {
                            pathmust "/core-model:clock-spec/core-model:";
                    require-instance false;
                        }
                must  'deref(.) = current()';
                        description     
                 "none";
                    }
                    description    
                "none";
                }



    /****************************************
    * package general-controller-model
    **************************************/ 
        /****************************************
        * package associations
        **************************************/ 

        /****************************************
        * grouping statements for object classes
        **************************************/ 
            /****************************************
            * package explanatory-classes
            **************************************/ 
                grouping compute-function {
                    description    
                "A generalized computational function with no particular specialization.
                        The specialization will be stated via a spec.";
                }
                grouping controlled-entity {
                    description    
                "The entity that is controlled by the controller at the focus of the view.
                        The entity may be an LTP, an FC etc.
                        Note that the controlled entity may be another controller.";
                }
                grouping control-policies {
                    description    
                "Policy governing the controller";
                }
                grouping control-function-abstraction {
                    uses processing-construct;
                    description    
                "The view of a functional component that forms part of the system that supports the ControlConstruct.
                        ControlConstructs are presented by the ControlConstruct itself to another ControlConstruct for the purpose of control of control.
                        ";
                }
                grouping controller-internal-view {
                    list subordinate-exposed-view {
                        uses subordinate-exposed-view;
                        description    
                "none";
                    }
                    description    
                "The view the controller has of the controller environment.";
                }
                grouping exposed-view-of-control-entities {
                    leaf-list control-function-abstraction {
                        type leafref {
                            pathmust "/core-model:control-function-abstraction/core-model:";
                    require-instance false;
                        }
                must  'deref(.) = current()';
                        description     
                 "none";
                    }
                    list control-port {
                        min-elements 1;
                        uses control-port;
                        description    
                "none";
                    }
                    uses constraint-domain;
                    description    
                "The presented view of the controller for the purpose of controlling the controller.";
                }
                grouping exposed-view-of-controlled-entities {
                    list control-port {
                        min-elements 1;
                        uses control-port;
                        description    
                "none";
                    }
                    leaf-list abstract-view {
                        type leafref {
                            pathmust "/core-model:abstract-view/core-model:";
                    require-instance false;
                        }
                must  'deref(.) = current()';
                        description     
                 "none";
                    }
                    leaf-list subordinate-exposed-view {
                        type leafref {
                            pathmust "/core-model:subordinate-exposed-view/core-model:";
                    require-instance false;
                        }
                must  'deref(.) = current()';
                        description     
                 "none";
                    }
                    description    
                "The view exposed of the controlled environment for the purpose of controlling the controlled environment via the controller.";
                }
                grouping abstract-view {
                    description    
                "none";
                }
                grouping exposed-view {
                    leaf exposed-view-of-control-entities {
                        type leafref {
                            pathmust "/core-model:exposed-view-of-control-entities/core-model:";
                    require-instance false;
                        }
                must  'deref(.) = current()';
                        description    
                    "none";
                    }
                    leaf exposed-view-of-controlled-entities {
                        type leafref {
                            pathmust "/core-model:exposed-view-of-controlled-entities/core-model:";
                    require-instance false;
                        }
                must  'deref(.) = current()';
                        description    
                    "none";
                    }
                    list port-to-controller {
                        min-elements 1;
                        uses control-port;
                        description    
                "none";
                    }
                    uses constraint-domain;
                    description    
                "none";
                }
                grouping subordinate-exposed-view {
                    container control-exposed-view {
                        uses exposed-view;
                        description    
                "none";
                    }
                    uses exposed-view;
                    description    
                "Is a pruned and refactored view of a view provided by a ControlConstruct subordinate to the ControlConstruct providing the ControlView.";
                }
                grouping function-network-element-control {
                    description    
                "Traditional model of the NE equivalent to an aspect of the NetworkElement class from v1.2.
                        This class should not be implemented.";
                }
                grouping function-sdn-controller {
                    description    
                "Traditional model of the SDN controller equivalent to the SdnController class from v1.2.
                        This class should not be implemented.";
                }
                grouping view-network-element-viewed-from-sdn-controller {
                    description    
                "Traditional model of the view of the NE controller as seen from a SDN Controller equivalent to an aspect of the NetworkElement class from v1.2.
                        This class should not be implemented.";
                }
                grouping view-sdn-controller-viewed-from-manager {
                    description    
                "Traditional model of the view of the SDN controller as seen from a manager .
                        No equivalent in v1.2.
                        This class should not be implemented.";
                }

            /****************************************
            * package control-port-interfacing
            **************************************/ 
                grouping control-task {
                    leaf problems-and-warnings {
                        type to-be-defined;
                        description    
                    "A list or problems and warnings related to the task.";
                    }
                    leaf time-to-completion {
                        type to-be-defined;
                        description    
                    "The estimated time to completion of the task.";
                    }
                    leaf task-lifecycle-state {
                        type task-lifecycle-state;
                        description    
                    "The state of the task (progress etc.).";
                    }
                    leaf activity-live-log {
                        type to-be-defined;
                        description    
                    "A log of activities.";
                    }
                    container request-context {
                        uses universal-request-constraint-structure;
                        description    
                "All details from the request.";
                    }
                    leaf-list control-task {
                        type leafref {
                            pathmust "/core-model:control-construct/core-model:control-tasks/core-model:";
                    require-instance false;
                        }
                must  'deref(.) = current()';
                        description     
                 "none";
                    }
                    description    
                "The representation of the task related to some request for activity or some spontaneous activity.";
                }
                grouping provider-role {
                    container provider-synchronous-port-role {
                        uses provider-synchronous-port-type;
                        description    
                "The UML port representing the provider role.";
                    }
                    container user-role {
                        uses user-role;
                        description    
                "none";
                    }
                    description    
                "Representation of the port activity where the ControlConstruct is acting as a provider.
                        A provider offers capabilities for others to use.";
                }
                grouping provider-synchronous-port-type {
                    description    
                "Exposes the synchronous communication capability of the provider aspect of the port.";
                }
                grouping user-role {
                    container user-synchronous-port-role {
                        uses user-synchronous-port-type;
                        description    
                "The UML port representing the user role.";
                    }
                    description    
                "Representation of the port activity where the ControlConstruct is acting as a user.
                        A user has needs that are satisfied by a provider.";
                }
                grouping user-synchronous-port-type {
                    description    
                "Exposes the synchronous communication capability of the user aspect of the port.";
                }

            grouping control-construct {
                leaf-list exposure-context {
                    type leafref {
                        pathmust "/core-model:exposure-context/core-model:";
                    require-instance false;
                    }
                must  'deref(.) = current()';
                    description     
                 "A view supported by the ControlConstruct that may be exposed at a ControlPort of the ControlConstruct.";
                }
                list defining-view-mapping {
                    min-elements 1;
                    uses view-mapping-function;
                    description    
                "ControlConstruct behavior is defined in part by view mappings.";
                }
                list control-port {
                    uses control-port;
                    description    
                "A port on the ControlConstruct that allows access to the functions of the ControlConstruct.";
                }
                leaf-list subordinate-control-construct-context {
                    type leafref {
                        pathmust "/core-model:control-construct/core-model:";
                    require-instance false;
                    }
                must  'deref(.) = current()';
                    description     
                 "A ControlConstruct that is part of an abstract view of the system that supports the referencing ControlConstruct and hence describes part of the behavior of the referencing ControlConstruct.";
                }
                leaf-list view-mapping {
                    type leafref {
                        pathmust "/core-model:view-mapping-function/core-model:";
                    require-instance false;
                    }
                must  'deref(.) = current()';
                    description     
                 "ControlConstruct uses the referenced ViewMapping to produce one view from another.";
                }
                list control-tasks {
                    uses control-task;
                    description    
                "An activity being carried out by the ControlConstruct where that activity is being exposed such that progress can be observed through a ControlPort.";
                }
                uses global-class;
                description    
                "Represents control capability/functionality.
                    ControlConstructs communicate with other ControlConstructs through ControlPorts about things within the related ConstraintDomains.
                    The ControlConstruct applies to all Control/Management cases including:
                    - the controller in the Network/Managed Element e.g. an SNMP agent).
                    - an SDN Controller.
                    - an EMS.
                    - an NMS.
                    This specific model follows a subset of the Component-System Pattern. 
                    ";
            }
            grouping control-port {
                leaf-list protecting-control-port {
                    type leafref {
                        pathmust "/core-model:control-construct/core-model:control-port/core-model:";
                    require-instance false;
                    }
                must  'deref(.) = current()';
                    description     
                 "A simple representation of resilience where one ControlPorts are identified as providing equivalent information.";
                }
                leaf control-port {
                    type leafref {
                        pathmust "/core-model:control-construct/core-model:control-port/core-model:";
                    require-instance false;
                    }
                must  'deref(.) = current()';
                    description    
                    "Control Ports may be used to associate controllers in a hierarchy and as peers.
                        Peer controllers are assumed to both the subordinate of each other.";
                }
                container ltp {
                    uses logical-termination-point;
                    description    
                "The LTP through which the control messaging/signaling flows.";
                }
                container provider-role {
                    uses provider-role;
                    description    
                "Properties relevant when the ControlPort is exposing the ControlConstruct as a provider of capability.";
                }
                container user-role {
                    uses user-role;
                    description    
                "Properties relevant when the ControlPort is exposing the ControlConstruct as a user of capability.";
                }
                list exposure-context {
                    uses exposure-context;
                    description    
                "A view presented through the ControlPort.";
                }
                description    
                "The access to the ControlConstruct following the normal Component-Port pattern (i.e., the functions of a component are accessed via ports).
                    Is assumed to usually be bidirectional.";
            }
            grouping view-mapping-function {
                list exposure-context {
                    min-elements 2;
                    max-elements 2;
                    uses exposure-context;
                    description    
                "An ExposureContext available to the ViewMappingFunction.";
                }
                list vmf-port {
                    uses vmf-port;
                    description    
                "A port of the ViewMappingFunction.";
                }
                description    
                "The rules that relate one view to another.
                    A ControlConstruct aggregates ViewMappingFunctions. 
                    Each ViewMappingFunction in the context of a ControlConstruct define the relationship between the views presented in an ExposureContext of that ControlConstruct and other views within the Controller.
                    The ViewMappingFunction is applied to the entities aggregated by one or more ConstraintDomains (via VmfPort - CdPort VmfMapsFromCdConstraintSet to construct the view in another ConstraintDomain (via VmfPort - CdPort VmfGovernsCdConstraintSet association).
                    For example, a pair of LTPs with matching adjacency tags in a nodal view may be mapped to a Link in a network view where the rules would describe the matching criteria etc.";
            }
            grouping exposure-context {
                container cd {
                    uses constraint-domain;
                    description    
                "The ConstraintDomain that defines the view to be exposed.";
                }
                description    
                "A view of the things controlled by a control system. For example, a virtual network of ONF TR-502, or more generally, resources (clause A.10 of ONF TR-521).
                    A referenced ConstraintDomain bounds a view which is a structured presentation of the underlying controlled things (the 'actual' entities) for some purpose.
                    The model bounded by the ConstraintDomain is constructed by mapping/abstracting the models of the underlying controlled things.
                    The ControlConstruct is itself controlled and presents itself in terms of ControlConstructs (subordinate) in a view.
                    At one extreme the referenced ConstraintDomain may expose all underlying details of everything controlled with no adjustment from the presentation provided by the controlled things.
                    A ConstraintDomain may expose a subset of the controlled things that focuses on a particular aspect (e.g., only the ControlConstructs).
                    A ControlPort has an association to the ExposureContext that explains, via the related ConstraintDomain, what can be acquired through the port
                    The emphasis is on exposing a constrained set of information and operations 
                    Bounds what is presented over an interface from a particular viewpoint. The domain of control is almost always broader than the entities etc. bounded by the ConstraintDomain. 
                    Represents the domain of control available to the viewer.";
            }
            grouping vmf-port {
                leaf vmf-port {
                    type leafref {
                        pathmust "/core-model:view-mapping-function/core-model:vmf-port/core-model:";
                    require-instance false;
                    }
                must  'deref(.) = current()';
                    description    
                    "Feeding to/from another Vmf.";
                }
                container source-cd-port {
                    uses cd-port;
                    description    
                "Drawing from a ConstraintDomain that aggregates classes to feed the mapping.";
                }
                container governed-cd-port {
                    uses cd-port;
                    description    
                "Causing instances of classes to be created/deleted/modified in the context of a ConstraintDomain that aggregates a view.
                        This governs what the ConstraintDomain may aggregate and also governs the lifecycle of the aggregated entities.";
                }
                description    
                "A port of the MappingFunction through which the effects of the mapping is exposed.
                    This can be an input to the mapping of as an output of the mapping where the inputs and outputs may have more detailed roles.";
            }

        /****************************************
        * package data-types
        **************************************/ 
            /****************************************
            * package control-port-interfacing
            **************************************/ 
                typedef task-lifecycle-state {
                    type identityref {
                        base TASK_LIFECYCLE_STATE;
                    }
                    description    
                "The potential states of the task.";
                }
                grouping universal-output-constraint-structure {
                    leaf progress-status {
                        type progress-status;
                        config false;
                        description    
                    "Indicates the progress of the task.";
                    }
                    container control-task {
                        config false;
                        uses control-task;
                        description    
                "none";
                    }
                    container structure-constraint {
                        config false;
                        uses operation-envelope;
                        description    
                "A universal structure to express the output from the task.";
                    }
                    container exposure-context {
                        config false;
                        uses exposure-context;
                        description    
                "none";
                    }
                    description    
                "A universal structure for representation of output from a task.";
                }
                grouping universal-request-constraint-structure {
                    container outcome-constraint {
                        config false;
                        uses operation-envelope;
                        description    
                "The definition of the constraint on the desired/agreed outcome.";
                    }
                    container exposure-context {
                        config false;
                        uses exposure-context;
                        description    
                "none";
                    }
                    description    
                "A universal structure for representation of the request to trigger a task.";
                }
                typedef progress-status {
                    type identityref {
                        base PROGRESS_STATUS;
                    }
                    description    
                "none";
                }


        /****************************************
        * package interfaces
        **************************************/ 
            rpc apply-system-structure-state-defined-by-constraint {
            description    
                  "none";
                input {
                    container input-constraint-structure {
                        uses universal-request-constraint-structure;
                        description    
                "none";
                    }
                }
                output {
                    container output-constraint-structure {
                        uses universal-output-constraint-structure;
                        description    
                "none";
                    }
                }
            }
            rpc retrieve-system-structure-defined-by-constraint {
            description    
                  "none";
                input {
                    container input-constraint-structure {
                        uses universal-request-constraint-structure;
                        description    
                "none";
                    }
                }
                output {
                    container output-constraint-structure {
                        uses universal-output-constraint-structure;
                        description    
                "none";
                    }
                }
            }


    /****************************************
    * package processing-construct-model
    **************************************/ 
        /****************************************
        * grouping statements for object classes
        **************************************/ 
            grouping processing-construct {
                list pc-port {
                    uses pc-port;
                    description    
                "An asymmetric PC instance is related to LTPs via PcPorts (essentially the ports of the PC). 
                        Symmetric PCs don't have PcPorts and are directly related to LTPs.";
                }
                list ltp {
                    uses logical-termination-point;
                    description    
                "A symmetric PC instance is associated with zero or more LTP objects.  
                        The LTPs on the PC boundary provide information for processing and capacity for communication. 
                        For asymmetric PCs the association to the LTP is via the PcPort (with stated role, allowing access to a specific function of the PC).";
                }
                leaf-list fd {
                    type leafref {
                        pathmust "/core-model:network-control-domain/core-model:network-element/core-model:fd/core-model:";
                    require-instance false;
                    }
                must  'deref(.) = current()';
                    description     
                 "One or more ForwardingDomains can constrain a ProcessingConstruct. 
                        A constrained PC connects LTPs on the boundary of the FD.";
                }
                leaf-list composed-pc {
                    type leafref {
                        pathmust "/core-model:processing-construct/core-model:";
                    require-instance false;
                    }
                must  'deref(.) = current()';
                    description     
                 "The PC class supports a recursive aggregation relationship (PcIsAssemblyOfPc).
                        This allows both:
                        - abstraction where an assembly of PCs (forming a System) is viewed as an abstract PC
                        - decomposition such that the internal construction of a PC can be exposed as multiple lower level PCs. 
                        Appropriate use of this association allows each of a collection of PCs to be decomposed into atomic parts (PCs) that can then be assembled into set of complex functions where each function in the set can be viewed as a PC.
                        Note that the model actually represents an aggregation of lower level PCs into higher level PCs as viewpoints rather than partitions, and supports multiple views.";
                }
                container pc-resilience-selector {
                    uses pc-resilience-selector;
                    description    
                "PcResilienceSelector that realizes the resilience of the PC.";
                }
                container running-software-process {
                    uses running-software-process;
                    description    
                "none";
                }
                container running-equipment {
                    uses equipment;
                    description    
                "none";
                }
                uses global-class;
                description    
                "ProcessingConstruct (PC) can be used to represent both potential and enabled processing between two or more of its PcPorts.
                    A PcPort may be associated with another PcPort or with an LTPs at a particular specific layerProtocol. 
                    Like the LTP, the PC supports any transport protocol including all circuit and packet forms. 
                    The PC is used to effect processing of information extracted from the transport layer protocol signal. 
                    A PC may be:
                    - Asymmetric such that it offers several functions and such that different functions are offered to different attached entities. 
                    - Symmetric such that it offers (or is considered as offering) only one function and the same function is offered to any attached entity with no interactions between functions offered to each attached entity
                    An asymmetric PC offering a number of distinct functions will have PcPorts through which the distinct functions are accessed.
                    A symmetric PC offering only a single function need not have PcPorts, the function can be accessed directly from the PC. ";
            }
            grouping cd-port {
                leaf cd-port {
                    type leafref {
                        pathmust "/core-model:constraint-domain/core-model:cd-port/core-model:";
                    require-instance false;
                    }
                must  'deref(.) = current()';
                    description    
                    "Constraint Domains can be meshed together view their ports directly as well as via LTPs indirectly.";
                }
                list ltp {
                    max-elements 2;
                    uses logical-termination-point;
                    description    
                "A CdPort is associated with zero or more LTP objects.  
                        The LTPs on the CD boundary provide capacity for processing. 
                        For symmetric CDs the association is directly from the CD to the LTP.";
                }
                leaf-list pc-port {
                    type leafref {
                        pathmust "/core-model:processing-construct/core-model:pc-port/core-model:";
                    require-instance false;
                    }
                must  'deref(.) = current()';
                    description     
                 "Where a CD is asymmetric and hence has CdPorts and where that CD supports PCs, appropriate CdPorts of that CD support the corresponding PcPorts.";
                }
                uses local-class;
                description    
                "The association of the CD to LTPs is direct for symmetric CDs and via CdPort for asymmetric CDs. 
                    The CdPort class models role based access to a CD.  
                    The capability to set up PCs between the associated CdPorts of a CD depends upon the type of CD. 
                    It is asymmetry in this capability that brings the need for CdPort.   
                    The CD can be considered as a component and the CdPort as a Port on that component.";
            }
            grouping pc-port {
                list ltp {
                    max-elements 2;
                    uses logical-termination-point;
                    description    
                "A PC instance is associated with zero or more LTP objects.  
                        The LTPs on the PC boundary provide capacity for processing. 
                        For asymmetric PCs the association to the LTP is via the PcPort.";
                }
                leaf-list pc-port {
                    type leafref {
                        pathmust "/core-model:processing-construct/core-model:pc-port/core-model:";
                    require-instance false;
                    }
                must  'deref(.) = current()';
                    max-elements 2;
                    description     
                 "A PcPort can be directly bound to another PcPort (rather than via a LTP) to support a simplified application level view (rather than requiring the full transport level view).";
                }
                list fc-port {
                    max-elements 2;
                    uses fc-port;
                    description    
                "A PcPort can be directly bound to an FcPort (rather than via a LTP) to support a simplified application level view (rather than requiring the full transport level view). 
                        This is used to represent complex semantic associations between PCs where _pcPort direct association is not sufficient.";
                }
                leaf port-role {
                    type string;
                    description    
                    "Identifies the role of the port in the context of the specification of the PC.";
                }
                uses local-class;
                description    
                "Represents the access to the functionality of a PC.";
            }
            grouping pc-resilience-selector {
                leaf-list pc {
                    type leafref {
                        pathmust "/core-model:processing-construct/core-model:";
                    require-instance false;
                    }
                must  'deref(.) = current()';
                    min-elements 2;
                    description     
                 "Alternative PC.";
                }
                uses local-class;
                description    
                "Rudimentary resilience model for PC.";
            }
            grouping constraint-domain {
                list cd-port {
                    uses cd-port;
                    description    
                "An asymmetric CD instance is related to LTPs via CdPorts (essentially the ports of the CD). 
                        Symmetric CDs don't have CdPorts and are directly related to LTPs.";
                }
                leaf-list pc-in-domain {
                    type leafref {
                        pathmust "/core-model:processing-construct/core-model:";
                    require-instance false;
                    }
                must  'deref(.) = current()';
                    description     
                 "A CD constrains one or more PCs. 
                        A constrained PC connects LTPs that are on the CD boundary.";
                }
                container ltp {
                    uses logical-termination-point;
                    description    
                "A symmetric CD instance is associated with zero or more LTP objects.  
                        The LTPs on the CD boundary provide capacity for processing. 
                        For asymmetric FDs the association to the LTP is via the FdPort.";
                }
                leaf-list cd-in-domain {
                    type leafref {
                        pathmust "/core-model:constraint-domain/core-model:";
                    require-instance false;
                    }
                must  'deref(.) = current()';
                    description     
                 "The CD class supports a recursive aggregation relationship such that the internal construction of an CD can be exposed as multiple lower level CDs. 
                        Note that the model actually represents an aggregation of lower level CDs into higher level CDs as viewpoints rather than partitions, and supports multiple views";
                }
                leaf-list casc-in-domain {
                    type leafref {
                        pathmust "/core-model:network-control-domain/core-model:network-element/core-model:ltp/core-model:embedded-clock/core-model:encapsulated-fc/core-model:configuration-and-switch-control/core-model:";
                    require-instance false;
                    }
                must  'deref(.) = current()';
                    description     
                 "A controller operating in the scope defined.";
                }
                leaf-list equipment-in-domain {
                    type leafref {
                        pathmust "/core-model:equipment/core-model:encapsulated-non-fru/core-model:";
                    require-instance false;
                    }
                must  'deref(.) = current()';
                    description     
                 "A ConstraintDomain can be used to represent physical constraints in the logical view. 
                        In this case the CD can be associated to the physical equipment.";
                }
                leaf-list fc-in-domain {
                    type leafref {
                        pathmust "/core-model:network-control-domain/core-model:network-element/core-model:ltp/core-model:embedded-clock/core-model:encapsulated-fc/core-model:";
                    require-instance false;
                    }
                must  'deref(.) = current()';
                    description     
                 "A CD constrains one or more FCs. 
                        A constrained FC connects LTPs that are on the CD boundary.";
                }
                leaf-list fd-in-domain {
                    type leafref {
                        pathmust "/core-model:network-control-domain/core-model:network-element/core-model:fd/core-model:";
                    require-instance false;
                    }
                must  'deref(.) = current()';
                    description     
                 "A CD constrains one or more FDs. 
                        A constrained FD connects LTPs that are on the CD boundary.";
                }
                leaf-list control-construct-in-domain {
                    type leafref {
                        pathmust "/core-model:control-construct/core-model:";
                    require-instance false;
                    }
                must  'deref(.) = current()';
                    description     
                 "A CD constrains one or more ControlConstructs.";
                }
                leaf-list ltp-in-domain {
                    type leafref {
                        pathmust "/core-model:network-control-domain/core-model:network-element/core-model:ltp/core-model:";
                    require-instance false;
                    }
                must  'deref(.) = current()';
                    description     
                 "A CD constrains one or more LTPs. ";
                }
                leaf-list link-in-domain {
                    type leafref {
                        pathmust "/core-model:link/core-model:";
                    require-instance false;
                    }
                must  'deref(.) = current()';
                    description     
                 "A CD constrains one or more Links. 
                        A constrained Link connects LTPs that are on the CD boundary.";
                }
                leaf-list running-os-in-domain {
                    type leafref {
                        pathmust "/core-model:running-operating-system/core-model:";
                    require-instance false;
                    }
                must  'deref(.) = current()';
                    description     
                 "A RunningOs constrained by the ConstraintDomain.";
                }
                leaf-list running-software-application-in-domain {
                    type leafref {
                        pathmust "/core-model:running-software-application/core-model:";
                    require-instance false;
                    }
                must  'deref(.) = current()';
                    description     
                 "A RunningSoftwareApplication constrained by the ConstraintDomain.";
                }
                leaf-list running-native-vmm-in-domain {
                    type leafref {
                        pathmust "/core-model:running-native-vmm/core-model:";
                    require-instance false;
                    }
                must  'deref(.) = current()';
                    description     
                 "A RunningVmm constrained by the ConstraintDomain.";
                }
                leaf-list file-system-in-domain {
                    type leafref {
                        pathmust "/core-model:file-system/core-model:";
                    require-instance false;
                    }
                must  'deref(.) = current()';
                    description     
                 "A FileSystem constrained by the ConstraintDomain.";
                }
                leaf-list vmf-in-domain {
                    type leafref {
                        pathmust "/core-model:view-mapping-function/core-model:";
                    require-instance false;
                    }
                must  'deref(.) = current()';
                    description     
                 "A ViewMappingFunction constrained by the ConstraintDomain.";
                }
                uses global-class;
                description    
                "ConstraintDomain (CD) models the topological component that represents the opportunity to enable processing of information between two or more of its CdPorts.
                    A CdPort may be associated with another CdPort or with an LTP at a particular specific layerProtocol. 
                    It provides the context for and constrains the formation, adjustment and removal of PCs and hence offers the potential to enable processing.  
                    The LTPs available are those defined at the boundary of the CD. 
                    A CD may be:
                    - Asymmetric such that it offers several functions and such that different functions are offered to different attached entities. 
                    - Symmetric such that it offers (or is considered as offering) only one function and the same function is offered to any attached entity with no interactions between functions offered to each attached entity
                    An asymmetric CD offering a number of distinct functions will have CdPorts through which the distinct functions are accessed.
                    A symmetric CD offering only a single function need not have CdPorts, the function can be accessed directly from the CD.";
            }

        /****************************************
        * package associations
        **************************************/ 


    /****************************************
    * package example-fragments
    **************************************/ 
        /****************************************
        * package core-management-control-construct-model
        **************************************/ 

        /****************************************
        * package core-operations-examples
        **************************************/ 
            /****************************************
            * package examples
            **************************************/ 
                /****************************************
                * package ltp
                **************************************/ 
                    /****************************************
                    * package pruned-model
                    **************************************/ 
                        grouping logical-termination-point {
                            leaf-list physical-port-reference {
                                type string;
                                description     
                 "One or more text labels for the unmodeled physical port associated with the LTP.
                                    In many cases there is no associated physical port";
                            }
                            leaf ltp-direction {
                                type termination-direction;
                                description    
                    "The overall directionality of the LTP. 
                                    - A BIDIRECTIONAL LTP must have at least some LPs that are BIDIRECTIONAL but may also have some SINK and/or SOURCE LPs.
                                    - A SINK LTP can only contain SINK LPs
                                    - A SOURCE LTP can only contain SOURCE LPs";
                            }
                            leaf uuid {
                                type universal-id;
                                config false;
                                description    
                    "UUID: An identifier that is universally unique.
                                    (This should be considered in the context of Identifier: A property of an entity/role with a value that is unique within an identifier space, where the identifier space is itself globally unique, and immutable. An identifier carries no semantics with respect to the purpose or state of the entity)";
                            }
                            list address {
                                uses address;
                                description    
                "One or more descriptions of the location.";
                            }
                            description    
                "none";
                        }
                        grouping name-and-value {
                            leaf value-name {
                                type string;
                                description    
                    "The name of the value. The value need not have a name.";
                            }
                            leaf value {
                                type string;
                                description    
                    "The value.";
                            }
                            description    
                "A scoped name-value pair";
                        }
                        typedef universal-id {
                            type string;
                            description    
                "The univeral ID value where the mechanism for generation is defned by some authority not directly referenced in the structure.";
                        }
                        typedef termination-direction {
                            type identityref {
                                base TERMINATION_DIRECTION;
                            }
                            description    
                "The directionality of a termination entity.";
                        }
                        grouping address-element {
                            leaf address-element-name {
                                type string;
                                description    
                    "none";
                            }
                            container local-id {
                                uses local-id-and-class;
                                description    
                "If the element is a localId (where the element above in the hierarchy must be the context in which the specific localId is relevant).";
                            }
                            leaf uuid {
                                type universal-id;
                                description    
                    "If the element is a uuid (where this element could be the top of a hierarchy but may also be at some level in the hierarchy where address navigation is considered necessary to assist in location of the UUID).";
                            }
                            container name {
                                uses name-and-class;
                                description    
                "If the element is a name.";
                            }
                            container address {
                                uses address;
                                description    
                "none";
                            }
                            leaf arbitrary-element {
                                type string;
                                description    
                    "Where the element is from some external model that is not formally represented in this model.";
                            }
                            description    
                "One element of a hierarchy of elements.
                                Note that the element must have one and only one value chosen from a list of potential value types.";
                        }
                        grouping address {
                            leaf address-name {
                                type string;
                                description    
                    "The name of the address (to allow the specific hierarchy to be distinguished from others for the same entity).";
                            }
                            list address-element {
                                uses address-element;
                                description    
                "none";
                            }
                            description    
                "A description of location via a hierarchy of narrowing contexts.";
                        }
                        grouping local-id-and-class {
                            leaf class-of-instance {
                                type string;
                                description    
                    "The class to which the name refers.";
                            }
                            container local-id {
                                uses name-and-value;
                                description    
                "The localId of the entity.";
                            }
                            description    
                "The localId and the class of entity that it identifies.";
                        }
                        grouping name-and-class {
                            leaf class-of-instance {
                                type string;
                                description    
                    "The class to which the name refers.";
                            }
                            container name {
                                uses name-and-value;
                                description    
                "If the element is a name.";
                            }
                            description    
                "The name and the class of entity that it names.";
                        }

                    /****************************************
                    * package instance-view-using-class-clones
                    **************************************/ 
                        grouping logical-termination-point-instance-constraints {
                            leaf-list physical-port-reference {
                                type string;
                                config false;
                                description     
                 "One or more text labels for the unmodeled physical port associated with the LTP.
                                    In many cases there is no associated physical port";
                            }
                            leaf ltp-direction {
                                type termination-direction;
                                default "TERMINATION_DIRECTION_SINK";
                                description    
                    "The overall directionality of the LTP. 
                                    - A BIDIRECTIONAL LTP must have at least some LPs that are BIDIRECTIONAL but may also have some SINK and/or SOURCE LPs.
                                    - A SINK LTP can only contain SINK LPs
                                    - A SOURCE LTP can only contain SOURCE LPs";
                            }
                            container address {
                                uses address;
                                description    
                "One or more descriptions of the location.";
                            }
                            leaf uuid {
                                type universal-id;
                                config false;
                                description    
                    "UUID: An identifier that is universally unique.
                                    (This should be considered in the context of Identifier: A property of an entity/role with a value that is unique within an identifier space, where the identifier space is itself globally unique, and immutable. An identifier carries no semantics with respect to the purpose or state of the entity)";
                            }
                            uses global-class;
                            description    
                "none";
                        }
                        grouping name-and-value {
                            leaf value-name {
                                type string;
                                description    
                    "The name of the value. The value need not have a name.";
                            }
                            leaf value {
                                type string;
                                description    
                    "The value.";
                            }
                            description    
                "A scoped name-value pair.";
                        }
                        typedef universal-id {
                            type string;
                            description    
                "The univeral ID value where the mechanism for generation is defned by some authority not directly referenced in the structure.";
                        }
                        typedef termination-direction {
                            type identityref {
                                base TERMINATION_DIRECTION;
                            }
                            description    
                "The directionality of a termination entity";
                        }
                        grouping global-class {
                            leaf-list local-id {
                                type string;
                                description     
                 "An identifier that is unique in the context of some scope that is less than the global scope.
                                    (This should be considered in the context of Identifier: A property of an entity/role with a value that is unique within an identifier space, where the identifier space is itself unique, and immutable. The identifier therefore represents the identity of the entity/role. An identifier carries no semantics with respect to the purpose of the entity.)";
                            }
                            leaf uuid {
                                type string;
                                config false;
                                description    
                    "UUID: An identifier that is universally unique.
                                    (This should be considered in the of Identifier: A property of an entity/role with a value that is unique within an identifier space, where the identifier space is itself globally unique, and immutable. An identifier carries no semantics with respect to the purpose or state of the entity)";
                            }
                            description    
                "Represents a type of thing (an Entity) that has instances which can exist in their own right (independently of any others).
                                Entity: Has identity, defined boundary, properties, functionality and lifecycle in a global context.
                                (This should be considered in the context of a Class: (usage) The representation of a thing that may be an entity or an inseparable Entity Feature).";
                        }
                        typedef string {
                            type string;
                            description    
                "String is a sequence of characters in some suitable character set used to display information about the model. Character sets may include non-Roman alphabets and characters.";
                        }
                        grouping address {
                            leaf address-name {
                                type string;
                                default "NeAddress";
                                description    
                    "The name of the address (to allow the specific hierarchy to be distinguished from others for the same entity).";
                            }
                            list address-element {
                                min-elements 2;
                                max-elements 2;
                                uses address-element-1;
                                description    
                "none";
                            }
                            description    
                "A description of location via a hierarchy of narrowing contexts.";
                        }
                        grouping address-element-1 {
                            leaf address-element-name {
                                type string;
                                description    
                    "none";
                            }
                            container local-id {
                                uses local-id-and-class;
                                description    
                "If the element is a localId (where the element above in the hierarchy must be the context in which the specific localId is relevant).";
                            }
                            leaf uuid {
                                type universal-id;
                                description    
                    "If the element is a uuid (where this element could be the top of a hierarchy but may also be at some level in the hierarchy where address navigation is considered necessary to assist in location of the UUID).";
                            }
                            container name {
                                uses name-and-class;
                                description    
                "If the element is a name.";
                            }
                            leaf arbitrary-element {
                                type string;
                                description    
                    "Where the element is from some external model that is not formally represented in this model.";
                            }
                            description    
                "One element of a hierarchy of elements.
                                Note that the element must have one and only one value chosen from a list of potential value types.";
                        }
                        grouping address-element-2 {
                            leaf address-element-name {
                                type string;
                                description    
                    "none";
                            }
                            container local-id {
                                uses local-id-and-class;
                                description    
                "If the element is a localId (where the element above in the hierarchy must be the context in which the specific localId is relevant).";
                            }
                            leaf uuid {
                                type universal-id;
                                description    
                    "If the element is a uuid (where this element could be the top of a hierarchy but may also be at some level in the hierarchy where address navigation is considered necessary to assist in location of the UUID).";
                            }
                            container name {
                                uses name-and-class;
                                description    
                "If the element is a name.";
                            }
                            leaf arbitrary-element {
                                type string;
                                description    
                    "Where the element is from some external model that is not formally represented in this model.";
                            }
                            description    
                "One element of a hierarchy of elements.
                                Note that the element must have one and only one value chosen from a list of potential value types.";
                        }

                    /****************************************
                    * package basic-conformant-operation
                    **************************************/ 
                        /****************************************
                        * package data-types
                        **************************************/ 
                            typedef action-verbs {
                                type identityref {
                                    base ACTION_VERBS;
                                }
                                description    
                "none";
                            }
                            typedef test-type {
                                type string;
                                description    
                "none";
                            }

                        /****************************************
                        * grouping statements for object classes
                        **************************************/ 
                            grouping operation-envelope {
                                container operation-identifiers {
                                    uses operation-identifiers;
                                    description    
                "none";
                                }
                                leaf action-verb {
                                    type action-verbs;
                                    default "ACTION_VERBS_CREATE_POST_ADD";
                                    description    
                    "none";
                                }
                                description    
                "none";
                            }
                            grouping operation-identifiers {
                                description    
                "none";
                            }
                            grouping desired-outcome-constraints {
                                list outcome-element {
                                    min-elements 1;
                                    uses outcome-element-constraints;
                                    description    
                "none";
                                }
                                description    
                "none";
                            }
                            grouping ltp {
                                description    
                "none";
                            }
                            grouping outcome-element-constraints {
                                container specific-class-structure {
                                    uses specific-class-structure;
                                    description    
                "none";
                                }
                                description    
                "none";
                            }
                            grouping specific-class-structure {
                                container class-type-name {
                                    uses ltp;
                                    description    
                "none";
                                }
                                description    
                "none";
                            }
                            grouping specific-pattern {
                                description    
                "none";
                            }





        /****************************************
        * package synchronization-of-timing
        **************************************/ 
            grouping clock {
                description    
                "none";
            }

        /****************************************
        * package profiles-templates-and-specifications-module
        **************************************/ 
            /****************************************
            * package spec-and-profile-sketch
            **************************************/ 
                grouping any-entity-instance {
                    list profile {
                        uses profile-instance;
                        description    
                "none";
                    }
                    container spec {
                        uses spec-instance;
                        description    
                "none";
                    }
                    container class {
                        uses any-entity-class;
                        description    
                "none";
                    }
                    description    
                "none";
                }
                grouping profile-instance {
                    container spec-instance {
                        uses spec-instance;
                        description    
                "none";
                    }
                    container profile-class {
                        uses profile-class;
                        description    
                "none";
                    }
                    container class {
                        uses any-entity-class;
                        description    
                "none";
                    }
                    description    
                "none";
                }
                grouping spec-instance {
                    container spec-class {
                        uses spec-class;
                        description    
                "none";
                    }
                    container class {
                        uses any-entity-class;
                        description    
                "none";
                    }
                    description    
                "none";
                }
                grouping any-entity-class {
                    description    
                "none";
                }
                grouping spec-class {
                    uses any-entity-class;
                    description    
                "none";
                }
                grouping profile-class {
                    uses any-entity-class;
                    description    
                "none";
                }



    /****************************************
    * package information-architecture-and-patterns
    **************************************/ 
        /****************************************
        * package patterns
        **************************************/ 
            /****************************************
            * package hypergraph
            **************************************/ 
                grouping hypergraph {
                    list hyper-edge {
                        min-elements 1;
                        uses hyper-edge;
                        description    
                "none";
                    }
                    list vertex {
                        uses vertex;
                        description    
                "none";
                    }
                    description    
                "none";
                }
                grouping hyper-edge {
                    list vertex {
                        uses vertex;
                        description    
                "none";
                    }
                    description    
                "none";
                }
                grouping vertex {
                    list hyper-edge {
                        min-elements 1;
                        uses hyper-edge;
                        description    
                "none";
                    }
                    description    
                "none";
                }
                grouping class-1 {
                    description    
                "none";
                }

            /****************************************
            * package constrained-hypergraph
            **************************************/ 
                grouping constrained-hypergraph {
                    list constrained-hyper-edge {
                        min-elements 1;
                        uses constrained-hyper-edge;
                        description    
                "none";
                    }
                    list constrained-vertex {
                        uses constrained-vertex;
                        description    
                "none";
                    }
                    description    
                "none";
                }
                grouping constrained-hyper-edge {
                    list constrained-vertex {
                        uses constrained-vertex;
                        description    
                "none";
                    }
                    list vertex-opportunity {
                        min-elements 1;
                        uses vertex-opportunity;
                        description    
                "none";
                    }
                    description    
                "none";
                }
                grouping constrained-vertex {
                    list constrained-hyper-edge {
                        min-elements 2;
                        max-elements 2;
                        uses constrained-hyper-edge;
                        description    
                "none";
                    }
                    list vertexopportunity {
                        min-elements 2;
                        max-elements 2;
                        uses vertex-opportunity;
                        description    
                "none";
                    }
                    description    
                "none";
                }
                grouping vertex-opportunity {
                    container constrainedvertex {
                        uses constrained-vertex;
                        description    
                "none";
                    }
                    description    
                "none";
                }

            /****************************************
            * package hypergraph-recursive-constrained-hypergraph
            **************************************/ 
                grouping constrained-hypergraph {
                    leaf-list constrained-hyper-edge {
                        type leafref {
                            pathmust "/core-model:constrained-hyper-edge/core-model:";
                    require-instance false;
                        }
                must  'deref(.) = current()';
                        min-elements 1;
                        description     
                 "none";
                    }
                    leaf-list constrained-vertex {
                        type leafref {
                            pathmust "/core-model:constrained-vertex/core-model:";
                    require-instance false;
                        }
                must  'deref(.) = current()';
                        description     
                 "none";
                    }
                    list vertex-opportunity {
                        uses vertex-opportunity;
                        description    
                "none";
                    }
                    list constrained-hyper-edge-view {
                        uses constrained-hyper-edge;
                        description    
                "none";
                    }
                    description    
                "none";
                }
                grouping constrained-hyper-edge {
                    list vertex-opportunity {
                        min-elements 1;
                        uses vertex-opportunity;
                        description    
                "none";
                    }
                    description    
                "none";
                }
                grouping constrained-vertex {
                    list vertexopportunity {
                        min-elements 2;
                        max-elements 2;
                        uses vertex-opportunity;
                        description    
                "none";
                    }
                    description    
                "none";
                }
                grouping vertex-opportunity {
                    container constrainedvertex {
                        uses constrained-vertex;
                        description    
                "none";
                    }
                    leaf-list vertex-opportunity {
                        type leafref {
                            pathmust "/core-model:constrained-hyper-edge/core-model:vertex-opportunity/core-model:";
                    require-instance false;
                        }
                must  'deref(.) = current()';
                        description     
                 "none";
                    }
                    description    
                "none";
                }

            /****************************************
            * package recursive-constrained-hypergraph-with-implicit-vertex
            **************************************/ 
                grouping constrained-hypergraph {
                    leaf-list constrained-hyper-edge {
                        type leafref {
                            pathmust "/core-model:constrained-hyper-edge/core-model:";
                    require-instance false;
                        }
                must  'deref(.) = current()';
                        min-elements 1;
                        description     
                 "none";
                    }
                    list vertex-opportunity {
                        uses vertex-opportunity;
                        description    
                "none";
                    }
                    list constrained-hyper-edge-view {
                        uses constrained-hyper-edge;
                        description    
                "none";
                    }
                    description    
                "none";
                }
                grouping constrained-hyper-edge {
                    list vertex-opportunity {
                        min-elements 1;
                        uses vertex-opportunity;
                        description    
                "none";
                    }
                    description    
                "none";
                }
                grouping vertex-opportunity {
                    leaf-list vertex-opportunity {
                        type leafref {
                            pathmust "/core-model:constrained-hyper-edge/core-model:vertex-opportunity/core-model:";
                    require-instance false;
                        }
                must  'deref(.) = current()';
                        description     
                 "none";
                    }
                    leaf vertex-opportunity {
                        type leafref {
                            pathmust "/core-model:constrained-hyper-edge/core-model:vertex-opportunity/core-model:";
                    require-instance false;
                        }
                must  'deref(.) = current()';
                        description    
                    "none";
                    }
                    description    
                "none";
                }

            /****************************************
            * package recasting-recursive-hypergraph-as-component-system
            **************************************/ 
                grouping system-hypergraph {
                    leaf-list component {
                        type leafref {
                            pathmust "/core-model:component-hyper-edge/core-model:";
                    require-instance false;
                        }
                must  'deref(.) = current()';
                        min-elements 1;
                        description     
                 "none";
                    }
                    list port {
                        uses port-vertex-opportunity;
                        description    
                "none";
                    }
                    list opaque-component-view {
                        uses component-hyper-edge;
                        description    
                "none";
                    }
                    description    
                "none";
                }
                grouping component-hyper-edge {
                    list port {
                        min-elements 1;
                        uses port-vertex-opportunity;
                        description    
                "none";
                    }
                    description    
                "none";
                }
                grouping port-vertex-opportunity {
                    leaf-list view-port {
                        type leafref {
                            pathmust "/core-model:component-hyper-edge/core-model:port/core-model:";
                    require-instance false;
                        }
                must  'deref(.) = current()';
                        description     
                 "none";
                    }
                    leaf port {
                        type leafref {
                            pathmust "/core-model:component-hyper-edge/core-model:port/core-model:";
                    require-instance false;
                        }
                must  'deref(.) = current()';
                        description    
                    "none";
                    }
                    leaf direction {
                        type direction;
                        description    
                    "none";
                    }
                    description    
                "none";
                }

            /****************************************
            * package directed-implicit-vertex
            **************************************/ 
                grouping constrained-hypergraph {
                    leaf-list constrained-hyper-edge {
                        type leafref {
                            pathmust "/core-model:constrained-hyper-edge/core-model:";
                    require-instance false;
                        }
                must  'deref(.) = current()';
                        min-elements 1;
                        description     
                 "none";
                    }
                    list vertex-opportunity {
                        uses vertex-opportunity;
                        description    
                "none";
                    }
                    container constrained-hyper-edge {
                        uses constrained-hyper-edge;
                        description    
                "none";
                    }
                    description    
                "none";
                }
                grouping constrained-hyper-edge {
                    list vertex-opportunity {
                        min-elements 1;
                        uses vertex-opportunity;
                        description    
                "none";
                    }
                    description    
                "none";
                }
                grouping vertex-opportunity {
                    leaf-list vertex-opportunity {
                        type leafref {
                            pathmust "/core-model:constrained-hyper-edge/core-model:vertex-opportunity/core-model:";
                    require-instance false;
                        }
                must  'deref(.) = current()';
                        description     
                 "none";
                    }
                    leaf vertex-opportunity {
                        type leafref {
                            pathmust "/core-model:constrained-hyper-edge/core-model:vertex-opportunity/core-model:";
                    require-instance false;
                        }
                must  'deref(.) = current()';
                        description    
                    "none";
                    }
                    leaf direction {
                        type direction;
                        description    
                    "none";
                    }
                    description    
                "none";
                }
                typedef direction {
                    type identityref {
                        base DIRECTION;
                    }
                    description    
                "none";
                }

            /****************************************
            * package constrained-directed-hypergraph
            **************************************/ 
                /****************************************
                * grouping statements for object classes
                **************************************/ 
                    grouping constrained-hyper-edge {
                        list constrained-vertex {
                            uses constrained-vertex;
                            description    
                "none";
                        }
                        list vertex-opportunity {
                            min-elements 1;
                            uses vertex-opportunity;
                            description    
                "none";
                        }
                        description    
                "none";
                    }
                    grouping constrained-hypergraph {
                        list constrained-hyper-edge {
                            min-elements 1;
                            uses constrained-hyper-edge;
                            description    
                "none";
                        }
                        list constrained-vertex {
                            uses constrained-vertex;
                            description    
                "none";
                        }
                        description    
                "none";
                    }
                    grouping constrained-vertex {
                        list constrained-hyper-edge {
                            min-elements 2;
                            max-elements 2;
                            uses constrained-hyper-edge;
                            description    
                "none";
                        }
                        list vertexopportunity {
                            min-elements 2;
                            max-elements 2;
                            uses vertex-opportunity;
                            description    
                "none";
                        }
                        description    
                "none";
                    }
                    grouping vertex-opportunity {
                        container constrainedvertex {
                            uses constrained-vertex;
                            description    
                "none";
                        }
                        leaf direction {
                            type direction;
                            description    
                    "none";
                        }
                        description    
                "none";
                    }


            /****************************************
            * package component-system-pattern
            **************************************/ 
                grouping component {
                    leaf-list bound-component {
                        type leafref {
                            pathmust "/core-model:component/core-model:";
                    require-instance false;
                        }
                must  'deref(.) = current()';
                        description     
                 "none";
                    }
                    leaf-list component-part {
                        type leafref {
                            pathmust "/core-model:component/core-model:";
                    require-instance false;
                        }
                must  'deref(.) = current()';
                        description     
                 "none";
                    }
                    list port {
                        uses port;
                        description    
                "none";
                    }
                    list boundary-port {
                        uses port;
                        description    
                "none";
                    }
                    description    
                "none";
                }
                grouping port {
                    leaf bound-port {
                        type leafref {
                            pathmust "/core-model:component/core-model:port/core-model:";
                    require-instance false;
                        }
                must  'deref(.) = current()';
                        description    
                    "none";
                    }
                    leaf-list aggregated-subordinate-port {
                        type leafref {
                            pathmust "/core-model:component/core-model:port/core-model:";
                    require-instance false;
                        }
                must  'deref(.) = current()';
                        description     
                 "none";
                    }
                    description    
                "none";
                }
                grouping system {
                    list boundary-port {
                        uses port;
                        description    
                "none";
                    }
                    leaf-list component-part {
                        type leafref {
                            pathmust "/core-model:component/core-model:";
                    require-instance false;
                        }
                must  'deref(.) = current()';
                        min-elements 1;
                        description     
                 "none";
                    }
                    container opaque-component {
                        uses component;
                        description    
                "none";
                    }
                    list system-port {
                        uses system-boundary-port;
                        description    
                "none";
                    }
                    description    
                "none";
                }
                grouping system-boundary-port {
                    leaf-list aggregated-port {
                        type leafref {
                            pathmust "/core-model:component/core-model:port/core-model:";
                    require-instance false;
                        }
                must  'deref(.) = current()';
                        min-elements 1;
                        description     
                 "none";
                    }
                    container component-port {
                        uses port;
                        description    
                "none";
                    }
                    description    
                "none";
                }

            /****************************************
            * package component-and-system-structure-sketch
            **************************************/ 
                /****************************************
                * grouping statements for object classes
                **************************************/ 
                    grouping attribute-package {
                        description    
                "none";
                    }
                    grouping component {
                        list port {
                            min-elements 1;
                            uses port;
                            description    
                "none";
                        }
                        list attribute-package {
                            uses attribute-package;
                            description    
                "none";
                        }
                        leaf-list bound-component {
                            type leafref {
                                pathmust "/core-model:component/core-model:";
                    require-instance false;
                            }
                must  'deref(.) = current()';
                            description     
                 "none";
                        }
                        container encapsulated-system {
                            uses system;
                            description    
                "none";
                        }
                        description    
                "none";
                    }
                    grouping indivisible-flow-port {
                        leaf indivisiblefow-port {
                            type leafref {
                                pathmust "/core-model:indivisible-flow-port/core-model:";
                    require-instance false;
                            }
                must  'deref(.) = current()';
                            description    
                    "none";
                        }
                        leaf role {
                            type string;
                            description    
                    "none";
                        }
                        list indivisible-port-role-properties {
                            min-elements 1;
                            uses indivisible-port-role-properties;
                            description    
                "none";
                        }
                        description    
                "none";
                    }
                    grouping multi-flow-port {
                        leaf-list indivisible-flow-port {
                            type leafref {
                                pathmust "/core-model:indivisible-flow-port/core-model:";
                    require-instance false;
                            }
                must  'deref(.) = current()';
                            min-elements 1;
                            description     
                 "none";
                        }
                        leaf-list multi-flow-port {
                            type leafref {
                                pathmust "/core-model:multi-flow-port/core-model:";
                    require-instance false;
                            }
                must  'deref(.) = current()';
                            description     
                 "none";
                        }
                        description    
                "none";
                    }
                    grouping port {
                        leaf role {
                            type string;
                            default "true";
                            description    
                    "none";
                        }
                        leaf bound-port {
                            type leafref {
                                pathmust "/core-model:component/core-model:port/core-model:";
                    require-instance false;
                            }
                must  'deref(.) = current()';
                            description    
                    "none";
                        }
                        container bound-component {
                            uses component;
                            description    
                "none";
                        }
                        container port-role-properties {
                            uses port-role-properties;
                            description    
                "none";
                        }
                        description    
                "none";
                    }
                    grouping port-role-properties {
                        description    
                "none";
                    }
                    grouping system {
                        description    
                "none";
                    }
                    grouping indivisible-port-role-properties {
                        description    
                "none";
                    }




    /****************************************
    * package core-interaction-model
    **************************************/ 
        /****************************************
        * package core-operations-model
        **************************************/ 
            /****************************************
            * package data-types
            **************************************/ 
                typedef action-verbs {
                    type identityref {
                        base ACTION_VERBS;
                    }
                    description    
                "Verb constructs that direct the activity.";
                }
                typedef test-type {
                    type string;
                    description    
                "none";
                }
                typedef activity-directive {
                    type identityref {
                        base ACTIVITY_DIRECTIVE;
                    }
                    description    
                "Explains how to interpret the request.";
                }
                typedef action-effort {
                    type identityref {
                        base ACTION_EFFORT;
                    }
                    description    
                "none";
                }
                typedef pause-resume-rule {
                    type identityref {
                        base PAUSE_RESUME_RULE;
                    }
                    description    
                "none";
                }

            /****************************************
            * grouping statements for object classes
            **************************************/ 
                grouping desired-outcome-constraints {
                    list outcome-element {
                        min-elements 1;
                        uses outcome-element-constraints;
                        description    
                "none";
                    }
                    leaf activity-directive {
                        type activity-directive;
                        default "ACTIVITY_DIRECTIVE_DEFINED_BY_VERB";
                        description    
                    "none";
                    }
                    leaf has-delete-confirmation {
                        type boolean;
                        default "true";
                        description    
                    "A delete confirmation exchange is required.";
                    }
                    leaf number-of-instances-of-each-outcome-element {
                type int64;
                        default "1";
                        description    
                    "The outcome statement defines a pattern where more than one instances of that pattern may be required.";
                    }
                    description    
                "none";
                }
                grouping element-constraints {
                    container specific-class-structure {
                        uses specific-class-structure;
                        description    
                "none";
                    }
                    container specific-pattern {
                        uses specific-pattern;
                        description    
                "none";
                    }
                    description    
                "none";
                }
                grouping general-directives {
                    description    
                "A structure of directives.";
                }
                grouping necessary-initial-condition-constraints {
                    leaf is-not {
                        type boolean;
                        default "false";
                        description    
                    "Qualifies a condition to be inverse, i.e. that something is not true rather than true prior commencing the task.";
                    }
                    description    
                "none";
                }
                grouping operation-details {
                    leaf action-verb {
                        type action-verbs;
                        description    
                    "Opportunity to provide an action verb to allow formation of a more traditional operation statement or a REST statement.";
                    }
                    list necessary-initial-condition-constraints {
                        uses necessary-initial-condition-constraints;
                        description    
                "none";
                    }
                    list desired-outcome-constraints {
                        min-elements 1;
                        uses desired-outcome-constraints;
                        description    
                "none";
                    }
                    description    
                "none";
                }
                grouping operation-envelope {
                    list operation-set {
                        min-elements 1;
                        uses operation-set;
                        description    
                "none";
                    }
                    container general-directives {
                        uses general-directives;
                        description    
                "General policy and other constraints to guide the operation execution.
                            Significant definition is required here.";
                    }
                    container operation-identifiers {
                        uses operation-identifiers;
                        description    
                "none";
                    }
                    description    
                "none";
                }
                grouping operation-identifiers {
                    description    
                "none";
                }
                grouping operation-set {
                    leaf-list operation-set-that-must-have-started {
                        type leafref {
                            pathmust "/core-model:operation-envelope/core-model:operation-set/core-model:";
                    require-instance false;
                        }
                must  'deref(.) = current()';
                        description     
                 "none";
                    }
                    leaf-list operation-set-that-must-end {
                        type leafref {
                            pathmust "/core-model:operation-envelope/core-model:operation-set/core-model:";
                    require-instance false;
                        }
                must  'deref(.) = current()';
                        description     
                 "none";
                    }
                    leaf abort-after-duration-with-action-rule {
                        type to-be-defined;
                        description    
                    "none";
                    }
                    leaf effort-and-action {
                        type action-effort;
                        default "ACTION_EFFORT_EXACT_MATCH";
                        description    
                    "none";
                    }
                    leaf pause-resume-rule {
                        type pause-resume-rule;
                        default "PAUSE_RESUME_RULE_NO_PAUSE_POSSIBLE";
                        description    
                    "none";
                    }
                    leaf-list operation-set {
                        type leafref {
                            pathmust "/core-model:operation-envelope/core-model:operation-set/core-model:";
                    require-instance false;
                        }
                must  'deref(.) = current()';
                        description     
                 "none";
                    }
                    leaf is-short-lived {
                        type boolean;
                        default "true";
                        description    
                    "none";
                    }
                    list operation-details {
                        min-elements 1;
                        uses operation-details;
                        description    
                "none";
                    }
                    description    
                "none";
                }
                grouping outcome-element-constraints {
                    uses element-constraints;
                    description    
                "none";
                }
                grouping specific-class-structure {
                    container class-type-name {
                        uses ltp;
                        description    
                "none";
                    }
                    description    
                "none";
                }
                grouping specific-pattern {
                    description    
                "none";
                }
                grouping ltp {
                    description    
                "none";
                }



    /****************************************
    * package core-software-model
    **************************************/ 
        /****************************************
        * grouping statements for object classes
        **************************************/ 
            /****************************************
            * package file-system
            **************************************/ 
                grouping file {
                    leaf size {
                        type string;
                        description    
                    "The size of the File, in bytes.";
                    }
                    leaf last-modify-time {
                        type yang:date-and-time;
                        description    
                    "The date time that the File was last modified.";
                    }
                    leaf checksum {
                        type string;
                        description    
                    "A checksum that can be used to validate the contents of the File (in case of corruption or malicious changes) using a hashing algorithm like MD5 or SHA1.";
                    }
                    uses file-system-entry;
                    description    
                "A File is a data structure used to store information (user data, commands, software etc.) in a computer system. Note that in this CIM class, we are only storing the metadata associated with the File, not the actual contents of the File.";
                }
                grouping file-system {
                    list file-system-entry {
                        uses file-system-entry;
                        description    
                "The root FileSystem entries, which can be Files or Directories.";
                    }
                    description    
                "A FileSystem organizes the data on a storage system so that it can be easily created, updated and accessed. It manages the Directories and also the metadata for the Files.";
                }
                grouping file-system-entry {
                    leaf is-read-only {
                        type boolean;
                        default "false";
                        description    
                    "If the File contents can be modified or not.";
                    }
                    leaf is-hidden {
                        type boolean;
                        default "false";
                        description    
                    "If the File is hidden by the FileSystem.";
                    }
                    leaf path-name {
                        type string;
                        description    
                    "The full pathname of the entry, back to the root Directory.";
                    }
                    leaf local-name {
                        type string;
                        description    
                    "The name of the entry in its Directory.";
                    }
                    leaf create-date {
                        type yang:date-and-time;
                        description    
                    "The date that the entry was created.";
                    }
                    description    
                "FileSystemEntry is an abstraction of File and Directory, useful when there is a need to reference both classes. It also allows for an easy representation of a hierarchical filesystem.";
                }
                grouping symbolic-link {
                    container file-system-entry {
                        uses file-system-entry;
                        description    
                "The FileSystemEntry that this SymbolicLink refers to.";
                    }
                    uses file;
                    description    
                "A SymbolicLink is a File that contains a path reference to a File or a Directory.";
                }
                grouping directory {
                    list file-system-entry {
                        uses file-system-entry;
                        description    
                "Directory entry, which can be a File or another Directory.";
                    }
                    uses file-system-entry;
                    description    
                "A Directory is a collection of Files and other Directories. Because a Directory can contain other Directories, this allows a hierarchical file system to be represented.";
                }

            /****************************************
            * package running-software
            **************************************/ 
                grouping installed-software-component {
                    leaf name {
                        type string;
                        description    
                    "The name of the installed component as returned by the operating system.";
                    }
                    leaf version {
                        type string;
                        description    
                    "The version of the installed component as returned by the operating system.";
                    }
                    leaf serial-number {
                        type string;
                        description    
                    "As part of software licensing, a serial number may be available for the installation.";
                    }
                    container installation-file {
                        uses file;
                        description    
                "If available, the File that the installation was from.";
                    }
                    leaf-list child-installed-software-component {
                        type leafref {
                            pathmust "/core-model:installed-software-component/core-model:child-installed-software-component/core-model:";
                    require-instance false;
                        }
                must  'deref(.) = current()';
                        description     
                 "References to any child installations.";
                    }
                    list installed-file-system-entry {
                        uses file-system-entry;
                        description    
                "References to any Directories or Files created or used by the installation. Note that installations may share files. So installation 1 may create key.dll in a common area, and installation 2 would create this if it wasn’t present. Because it is already present, installation 2 just references the file. Now if installation 1 is uninstalled, key.dll is not removed as there is still a reference to it.";
                    }
                    description    
                "InstalledSoftwareComponent is part of the software inventory. It represents an application or an application suite or an application (feature) option. It is the unit of installation. Note that this is operating system dependent. For example, Microsoft DOS 3.3 didn’t have an installation manager.";
                }
                grouping running-software-process {
                    leaf process-id {
                        type string;
                        description    
                    "The identifier provided by the operating system.";
                    }
                    leaf priority {
                        type string;
                        description    
                    "The process priority which is used by a multi-tasking operating system to assign resource allocations for the different running software processes.";
                    }
                    leaf invoking-user {
                        type string;
                        description    
                    "The username of the account that invoked the process.";
                    }
                    leaf invoking-command {
                        type string;
                        description    
                    "The command string that invoked the process.";
                    }
                    leaf time-invoked {
                        type date-and-time;
                        description    
                    "The date time when the process was invoked.";
                    }
                    leaf run-state {
                        type string;
                        description    
                    "The current run state. A software process may be actively running or suspended (or some other state supported by the operating system).";
                    }
                    leaf name {
                        type string;
                        description    
                    "The name of the process as assigned by the operating system.";
                    }
                    leaf description {
                        type string;
                        description    
                    "The description of the process as assigned by the operating system.";
                    }
                    container executable {
                        uses file;
                        description    
                "A reference to the executable file (invoked via the invokingCommand). Note that the invoking command may not list the full file path.";
                    }
                    leaf-list child-software-process {
                        type string;
                        description     
                 "References to a software process’s subprocesses and threads.";
                    }
                    list open-file {
                        uses file;
                        description    
                "References to any files opened and/or locked by the running process.";
                    }
                    description    
                "This is the unit of software execution. It could be a running application or a thread (the smallest level of software execution).";
                }
                grouping running-operating-system {
                    list running-software-process {
                        uses running-software-process;
                        description    
                "The software processes running under this operating system.";
                    }
                    list running-container-engine {
                        uses running-container-engine;
                        description    
                "The running container engines supported by the running operating system.";
                    }
                    list running-host-os-vmm {
                        uses running-host-os-vmm;
                        description    
                "The host OS VMMs running under this operating system.";
                    }
                    uses running-software-process;
                    description    
                "An operating system is a running software process that enables software applications to utilize the computer’s hardware.";
                }
                grouping running-software-application {
                    uses running-software-process;
                    description    
                "This covers generic software processes that don’t have a special subclass (operating system, virtual machine and container special cases have their own specific subclasses).";
                }

            /****************************************
            * package virtual-machine
            **************************************/ 
                grouping running-host-os-vmm {
                    uses running-virtual-machine-monitor;
                    description    
                "A Virtual Machine Monitor (VMM or Hypervisor) running in a host operating system (type-2).";
                }
                grouping running-native-vmm {
                    uses running-virtual-machine-monitor;
                    description    
                "A Virtual Machine Monitor (VMM or Hypervisor) running directly on the hardware (bare metal or type-1).";
                }
                grouping running-virtual-machine {
                    container vm-boundary {
                        uses constraint-domain;
                        description    
                "Similar to a physical device boundary, we allow a virtual machine to have a constraint boundary.";
                    }
                    description    
                "This represents a VirtualMachine that is running, and hence can provide and consume resources. It isn’t shown as a subclass of RunningSoftwareProcess as it may not be a running software process and the hypervisor may not allow access to any process related information.";
                }
                grouping running-virtual-machine-monitor {
                    list running-vm {
                        uses running-virtual-machine;
                        description    
                "The VMs actively running under this VMM.";
                    }
                    uses running-software-process;
                    description    
                "This is the abstraction of the two different types of VMM.";
                }

            /****************************************
            * package software-container
            **************************************/ 
                grouping running-container {
                    container container-boundary {
                        uses constraint-domain;
                        description    
                "The constraints defining the boundary of the Container.";
                    }
                    uses running-software-process;
                    description    
                "A container that has been activated by its container engine and hence can provide and consume resources.";
                }
                grouping running-container-engine {
                    list running-container {
                        uses running-container;
                        description    
                "The containers running in this container engine.";
                    }
                    uses running-software-process;
                    description    
                "A software process that abstracts running applications from the operating system. It provides some level of isolation, but not as much as a hypervisor.";
                }


        /****************************************
        * package associations
        **************************************/ 

/****************************************
* typedef statements
**************************************/ 

/*********************************************
* grouping statements for complex data types
*******************************************/ 
            identity PORT_DIRECTION {
                description    
                "none";
            }
            identity PORT_DIRECTION_BIDIRECTIONAL {
                base PORT_DIRECTION;
                description    
                "The Port has both an INPUT flow and an OUTPUT flow defined.";
            }
            identity PORT_DIRECTION_INPUT {
                base PORT_DIRECTION;
                description    
                "The Port only has definition for a flow into the Forwarding entity (i.e. an ingress flow).";
            }
            identity PORT_DIRECTION_OUTPUT {
                base PORT_DIRECTION;
                description    
                "The Port only has definition for a flow out of the Forwarding entity (i.e. an egress flow).";
            }
            identity PORT_DIRECTION_UNIDENTIFIED_OR_UNKNOWN {
                base PORT_DIRECTION;
                description    
                "Not a normal state. The system is unable to determine the correct value.";
            }
            identity PORT_DIRECTION_OMNIDIRECTIONAL {
                base PORT_DIRECTION;
                description    
                "none";
            }
            identity FORWARDING_DIRECTION {
                description    
                "none";
            }
            identity FORWARDING_DIRECTION_BIDIRECTIONAL {
                base FORWARDING_DIRECTION;
                description    
                "The Forwarding entity supports both BIDIRECTIONAL flows at all Ports (i.e. all Ports have both an INPUT flow and an OUTPUT flow defined).";
            }
            identity FORWARDING_DIRECTION_UNIDIRECTIONAL {
                base FORWARDING_DIRECTION;
                description    
                "The Forwarding entity has Ports that are either INPUT or OUTPUT. It has no BIDIRECTIONAL Ports.";
            }
            identity FORWARDING_DIRECTION_UNDEFINED_OR_UNKNOWN {
                base FORWARDING_DIRECTION;
                description    
                "Not a normal state. The system is unable to determine the correct value.";
            }
            identity FORWARDING_DIRECTION_OMNIDIRECTIONAL {
                base FORWARDING_DIRECTION;
                description    
                "none";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base TERMINATION_DIRECTION;
                description    
                "Not a normal state. The system is unable to determine the correct value.";
            }
            identity EXTENDED_TERMINATION_DIRECTION {
                description    
                "none";
            }
            identity EXTENDED_TERMINATION_DIRECTION_CONTRA_DIRECTION_SINK {
                base EXTENDED_TERMINATION_DIRECTION;
                description    
                "The essential flow of the Termination entity is SINK (i.e. up the layer stack) but the INPUT flow of the Termination entity was provided by a SOURCE OUTPUT or taken from a SOURCE INPUT (duplicating the input signal) hence reversing the flow orientation from down the layer stack to up the layer stack.";
            }
            identity EXTENDED_TERMINATION_DIRECTION_CONTRA_DIRECTION_SOURCE {
                base EXTENDED_TERMINATION_DIRECTION;
                description    
                "The essential flow of the Termination entity is SOURCE (i.e. down the layer stack) but the OUTPUT flow of the Termination entity was fed to (and replaces) a SINK OUTPUT or was fed to a SINK INPUT (replacing the normal flow) hence reversing the flow orientation from down the layer stack to up the layer stack.";
            }
            identity TERMINATION_STATE {
                description    
                "none";
            }
            identity TERMINATION_STATE_LP_CAN_NEVER_TERMINATE {
                base TERMINATION_STATE;
                description    
                "A non-flexible case that can never be terminated.";
            }
            identity TERMINATION_STATE_LP_NOT_TERMINATED {
                base TERMINATION_STATE;
                description    
                "A flexible termination that can terminate but is currently not terminated.";
            }
            identity TERMINATION_STATE_TERMINATED_SERVER_TO_CLIENT_FLOW {
                base TERMINATION_STATE;
                description    
                "A flexible termination that is currently terminated for server to client flow only.";
            }
            identity TERMINATION_STATE_TERMINATED_CLIENT_TO_SERVER_FLOW {
                base TERMINATION_STATE;
                description    
                "A flexible termination that is currently terminated for client to server flow only.";
            }
            identity TERMINATION_STATE_TERMINATED_BIDIRECTIONAL {
                base TERMINATION_STATE;
                description    
                "A flexible termination that is currently terminated in both directions of flow.";
            }
            identity TERMINATION_STATE_LP_PERMENANTLY_TERMINATED {
                base TERMINATION_STATE;
                description    
                "A non-flexible termination that is always terminated (in both directions of flow for a bidirectional case and in the one direction of flow for both unidirectional cases).";
            }
            identity TERMINATION_STATE_TERMINATION_STATE_UNKNOWN {
                base TERMINATION_STATE;
                description    
                "There TerminationState cannot be determined.";
            }
            identity PROTECTION_REASON {
                description    
                "none";
            }
            identity PROTECTION_REASON_WAIT_TO_REVERT {
                base PROTECTION_REASON;
                description    
                "The resource is selected as control is waiting to restore to a preferred resource.";
            }
            identity PROTECTION_REASON_SIGNAL_DEGRADE {
                base PROTECTION_REASON;
                description    
                "The resource is selected as the best preferred resource is in signal degrade.";
            }
            identity PROTECTION_REASON_SIGNAL_FAIL {
                base PROTECTION_REASON;
                description    
                "The resource is selected as the best preferred resource is in signal fail.";
            }
            identity ROUTE_SELECTION_CONTROL {
                description    
                "none";
            }
            identity ROUTE_SELECTION_CONTROL_LOCK_OUT {
                base ROUTE_SELECTION_CONTROL;
                description    
                "The resource is configured to temporarily not be available for use in the protection scheme(s) it is part of.
                    This overrides all other protection control states including forced.
                    If the item is locked out, then it cannot be used under any circumstances.
                    Note: Only relevant when part of a protection scheme.
                    Note: if a protection process that has a relationship to the item (i.e. is one of the options the protection process may choose) is deactivated by being isFrozen = true) then the lockout request will be rejected. ";
            }
            identity ROUTE_SELECTION_REASON {
                description    
                "none";
            }
            identity SWITCH_CONTROL {
                description    
                "none";
            }
            identity SWITCH_CONTROL_NORMAL {
                base SWITCH_CONTROL;
                description    
                "No administrative control applied to the switch.";
            }
            identity SWITCH_CONTROL_MANUAL {
                base SWITCH_CONTROL;
                description    
                "Resource temporarily chosen by control configuration where the resource is not the preferred resource.
                    Preferred resource has highest priority.
                    Temporarily overrides reversion.
                    If this resource fails, it will switch to best available resource. 
                    If resource selected is shared and another FC requires the resource, then the selection control will change to Normal and switch to best available based upon normal rules.
                    Cannot manually switch a Forced switch, cannot remove a forced switch, cannot switch to a locked out item and will be rejected if the protection process is deactivated by being Freeze = true).
                    A manual switch/route that is selecting an FcPort, LTP, FC, Link or Route that is subsequently set to LOCK_OUT will have the manual removed (changed to NORMAL) and will switch away from the FcPort with LOCK_OUT to best available based upon normal rules.
                    A manual switch that is selecting an FcPort that is subsequently selected by a Forced switch will be restored to normal operation and the manual will be removed.
                    A manual switch/route that is selecting an FcPort, LTP, FC, Link or Route that is subsequently manual selected by another switch/route will have the manual removed and will switch away from the FcPort.
                    Can be returned to NORMAL by configuration action.";
            }
            identity SWITCH_CONTROL_FORCED {
                base SWITCH_CONTROL;
                description    
                "Resource temporarily chosen by control configuration where the resource is not the preferred resource.
                    Preferred resource has highest priority.
                    Temporarily overrides reversion.
                    If this resource fails it will NOT switch. 
                    If resource selected is shared and another FC requires the resource through a FORCE on that FC and the FC is of a higher FcPriority then the selection control on this FC will change to NORMAL and switch to best available based upon normal rules.
                    If the resource selected is then set to LOCK_OUT then the selection control will change to NORMAL and switch to best available based upon normal rules.
                    Can be returned to NORMAL by configuration action.";
            }
            identity SWITCH_STATE_REASON {
                description    
                "none";
            }
            identity REVERSION_MODE {
                description    
                "none";
            }
            identity REVERSION_MODE_REVERTIVE {
                base REVERSION_MODE;
                description    
                "An FC switched to a lower priority (non-preferred) resource will revert to a higher priority (preferred) resource when that recovers (potentially after some hold-off time).";
            }
            identity REVERSION_MODE_NON-REVERTIVE {
                base REVERSION_MODE;
                description    
                "An FC switched to a lower priority (non-preferred) resource will not revert to a higher priority (preferred) resource when that recovers.";
            }
            identity RESILIENCE_CONTROL {
                description    
                "none";
            }
            identity RESILIENCE_CONTROL_QUIESCENT {
                base RESILIENCE_CONTROL;
                description    
                "none";
            }
            identity RESILIENCE_CONTROL_RESTORING {
                base RESILIENCE_CONTROL;
                description    
                "none";
            }
            identity RESILIENCE_CONTROL_RECOVERY_FAILED {
                base RESILIENCE_CONTROL;
                description    
                "none";
            }
            identity RESILIENCE_CONTROL_UNKNOWN {
                base RESILIENCE_CONTROL;
                description    
                "none";
            }
            identity RUN_MODE {
                description    
                "none";
            }
            identity RUN_MODE_FREE_RUN {
                base RUN_MODE;
                description    
                "The clock is not synchronized to another clock.";
            }
            identity RUN_MODE_LOCKED {
                base RUN_MODE;
                description    
                "The clock is synchronized to another clock.";
            }
            identity RUN_MODE_HOLD_OVER {
                base RUN_MODE;
                description    
                "The clock was previously synchronized to another clock but that timing input has been lost.
                    The clock is set to the last known synchronization.";
            }
            identity LAYER_PROTOCOL_NAME {
                description    
                "none";
            }
            identity LAYER_PROTOCOL_NAME_PHOTONIC_MEDIA {
                base LAYER_PROTOCOL_NAME;
                description    
                "The characteristic information is that of a channel able to carry photons and of the photon source/sink.";
            }
            identity LAYER_PROTOCOL_NAME_OTU_AND_ODU {
                base LAYER_PROTOCOL_NAME;
                description    
                "The characteristic information is that of a channel able to carry ODU/OTU protocol (OTN) and of the ODU/OTU source/sink.";
            }
            identity LAYER_PROTOCOL_NAME_ETHERNET {
                base LAYER_PROTOCOL_NAME;
                description    
                "The characteristic information is that of a channel able to carry Ethernet protocol and of the Ethernet protocol source/sink.";
            }
            identity OPERATIONAL_STATE {
                description    
                "none";
            }
            identity OPERATIONAL_STATE_DISABLED {
                base OPERATIONAL_STATE;
                description    
                "The resource is unable to meet the SLA of the user of the resource. 
                    If no (explicit) SLA is defined the resource is disabled if it is totally inoperable and unable to provide service to the user.";
            }
            identity OPERATIONAL_STATE_ENABLED {
                base OPERATIONAL_STATE;
                description    
                "The resource is partially or fully operable and available for use.";
            }
            identity ADMINISTRATIVE_STATE {
                description    
                "none";
            }
            identity ADMINISTRATIVE_STATE_LOCKED {
                base ADMINISTRATIVE_STATE;
                description    
                "Users are administratively prohibited from making use of the resource.";
            }
            identity ADMINISTRATIVE_STATE_UNLOCKED {
                base ADMINISTRATIVE_STATE;
                description    
                "Users are allowed to use the resource.";
            }
            identity ADMINISTRATIVE_STATE_SHUTTING_DOWN {
                base ADMINISTRATIVE_STATE;
                description    
                "The entity is administratively restricted to existing instances of use only. There may be specific actions to remove existing uses. No new instances of use can be enabled.
                    The resource automatically transitions to “locked” when the last user quits. 
                    The administrative state is not visible in the client context. 
                    The lifecycle state “pending removal” should be used to indicate to the client that the provider intends to remove the resource.";
            }
            identity ADMINISTRATIVE_CONTROL {
                description    
                "none";
            }
            identity ADMINISTRATIVE_CONTROL_UNLOCK {
                base ADMINISTRATIVE_CONTROL;
                description    
                "The intention is for the entity to become unlocked.
                    The entity may already be UNLOCKED.";
            }
            identity ADMINISTRATIVE_CONTROL_LOCK_PASSIVE {
                base ADMINISTRATIVE_CONTROL;
                description    
                "The intention is for the entity to become locked but no effort is expected to move to the Locked state (the state will be achieved once all users stop using the resource). 
                    The entity may be LOCKED.";
            }
            identity ADMINISTRATIVE_CONTROL_LOCK_ACTIVE {
                base ADMINISTRATIVE_CONTROL;
                description    
                "The intention is for the entity to become locked and it is expected that effort will be made to move to the Locked state (users will be actively removed). 
                    The entity may already be LOCKED.";
            }
            identity ADMINISTRATIVE_CONTROL_LOCK_IMMEDIATE {
                base ADMINISTRATIVE_CONTROL;
                description    
                "The intention is for the entity to become locked and it is expected to move to the Locked state immediately (users will be force removed). 
                    The entity may already be LOCKED.";
            }
            identity ADMINISTRATIVE_CONTROL_QUIESCENT {
                base ADMINISTRATIVE_CONTROL;
                description    
                "The administrative state is at a stable value (LOCKED/UNLOCKED) and no action is being taken.";
            }
            identity LIFECYCLE_STATE {
                description    
                "none";
            }
            identity LIFECYCLE_STATE_PLANNED {
                base LIFECYCLE_STATE;
                description    
                "The resource is planned but is not present in the network.
                    Should include a 'time' when the resources are expected to be installed.";
            }
            identity LIFECYCLE_STATE_POTENTIAL_AVAILABLE {
                base LIFECYCLE_STATE;
                description    
                "The supporting resources are present in the network but are shared with other clients; or require further configuration before they can be used; or both.
                    (1) When a potential resource is configured and allocated to a client it is moved to the INSTALLED state for that client.
                    (2) If the potential resource has been consumed (e.g. allocated to another client) it is moved to the POTENTIAL BUSY state for all other clients.";
            }
            identity LIFECYCLE_STATE_POTENTIAL_BUSY {
                base LIFECYCLE_STATE;
                description    
                "The supporting resources are present in the network but have been allocated to other clients.";
            }
            identity LIFECYCLE_STATE_INSTALLED {
                base LIFECYCLE_STATE;
                description    
                "The resource is present in the network and is capable of providing the service.";
            }
            identity LIFECYCLE_STATE_PENDING_REMOVAL {
                base LIFECYCLE_STATE;
                description    
                "The resource has been marked for removal. Should include a “time” when the resources are expected to be removed.";
            }
            identity BLOCK_DIRECTION {
                description    
                "none";
            }
            identity BLOCK_DIRECTION_NO_BLOCK {
                base BLOCK_DIRECTION;
                description    
                "The FC is not blocking signal related to the LTP.";
            }
            identity BLOCK_DIRECTION_INGRESS_BLOCK {
                base BLOCK_DIRECTION;
                description    
                "The FC is blocking signal that is flowing into the LTP from the FC.";
            }
            identity BLOCK_DIRECTION_EGRESS_BLOCK {
                base BLOCK_DIRECTION;
                description    
                "The FC is blocking signal flowing out of the LTP to the FC.";
            }
            identity BLOCK_DIRECTION_BIDIRECTIONAL_BLOCK {
                base BLOCK_DIRECTION;
                description    
                "The FC is blocking both directions of traffic, i.e. Ingress and Egress, to/from the LTP.";
            }
            identity CONNECTOR_AND_PIN_ORIENTATION {
                description    
                "none";
            }
            identity CONNECTOR_AND_PIN_ORIENTATION_MALE {
                base CONNECTOR_AND_PIN_ORIENTATION;
                description    
                "The connecting elements are dominantly protrusions.";
            }
            identity CONNECTOR_AND_PIN_ORIENTATION_FEMALE {
                base CONNECTOR_AND_PIN_ORIENTATION;
                description    
                "The connecting elements are dominantly indentations.";
            }
            identity CONNECTOR_AND_PIN_ORIENTATION_SYMMETRIC_NEUTRAL {
                base CONNECTOR_AND_PIN_ORIENTATION;
                description    
                "The pin (and housing) orientation combination is such that it is symmetric so a connector is compatible with itself.
                    The connecting element may be a surface rather than protrusions or indentations.";
            }
            identity EQUIPMENT_CATEGORY {
                description    
                "none";
            }
            identity EQUIPMENT_CATEGORY_SUBRACK {
                base EQUIPMENT_CATEGORY;
                description    
                "An assembly with holders designed to accommodate CIRCUIT_PACKs. 
                    The assembly is designed to be mounted in a RACK.";
            }
            identity EQUIPMENT_CATEGORY_CIRCUIT_PACK {
                base EQUIPMENT_CATEGORY;
                description    
                "An assembly with connectors compatible with those in a holder.
                    The assembly is designed to be mounted in a holder (SLOT) of a SUBRACK.
                    May also support holders (SLOTs) for SMALL_FORMFACTOR_PLUGGABLEs.";
            }
            identity EQUIPMENT_CATEGORY_SMALL_FORMFACTOR_PLUGGABLE {
                base EQUIPMENT_CATEGORY;
                description    
                "A small assembly (compared to a CIRCUIT_PACK) with connectors compatible with those in a holder.
                    The assembly is designed to be mounted in a holder (SLOT) of a CIRCUIT_PACK or STAND_ALONE_UNIT.";
            }
            identity EQUIPMENT_CATEGORY_STAND_ALONE_UNIT {
                base EQUIPMENT_CATEGORY;
                description    
                "An assembly with connectors for cabling and potentially with holders.
                    The assembly is designed to be mounted in a freeform environment (on a table or simple mechanical cabinet).
                    May support holders (SLOTs) for CIRCUIT_PACKs or for SMALL_FORMFACTOR_PLUGGABLEs.";
            }
            identity EQUIPMENT_CATEGORY_RACK {
                base EQUIPMENT_CATEGORY;
                description    
                "A mechanical assembly with cabling and predefined mounting points for particular SUBRACK types.
                    The assembly is designed to be mounted on the floor in a row with other RACKs.";
            }
            identity HOLDER_CATEGORY {
                description    
                "none";
            }
            identity HOLDER_CATEGORY_SLOT {
                base HOLDER_CATEGORY;
                description    
                "A guided holder with fixed connectors.
                    The guided holder is designed to take a particular form of CIRCUIT_PACK or SMALL_FORMFACTOR_PLUGGABLE";
            }
            identity FORWARDING_RULE {
                description    
                "none";
            }
            identity FORWARDING_RULE_CANNOT_FORWARD_ACROSS_FD_LINK {
                base FORWARDING_RULE;
                description    
                "LTPs referenced by the FD (or indirectly by the Link between FDs) cannot have FCs created between them.
                    This rule overrides all others.";
            }
            identity FORWARDING_RULE_MUST_FORWARD_ACROSS_FD_LINK {
                base FORWARDING_RULE;
                description    
                "LTPs referenced by the FD (or indirectly by the Link between FDs) MUST have FCs created between them.
                    This rule overrides all others except the CANNOT_FORWARD rule.";
            }
            identity FORWARDING_RULE_MAY_FORWARD_ACROSS_FD_LINK {
                base FORWARDING_RULE;
                description    
                "LTPs referenced by the FD (or indirectly by the Link between FDs) may have FCs created between them.
                    FCs may not be created between points that are not related by this rule either directly in an FD or indirectly via a Link linking two or more FDs.
                    For a Link points in an FD at one end of the Link can be connected to points in an FD at an other end of the Link.";
            }
            identity FORWARDING_RULE_NULL_FORWARDING_RULE {
                base FORWARDING_RULE;
                description    
                "none";
            }
            identity RULE_TYPE {
                description    
                "none";
            }
            identity RULE_TYPE_FORWARDING {
                base RULE_TYPE;
                description    
                "The rule relates to creation of FCs.";
            }
            identity RULE_TYPE_COST {
                base RULE_TYPE;
                description    
                "The rule relates to forwarding cost.";
            }
            identity RULE_TYPE_RISK {
                base RULE_TYPE;
                description    
                "The rule relates to forwarding risk.";
            }
            identity RULE_TYPE_CAPACITY {
                base RULE_TYPE;
                description    
                "none";
            }
            identity PORT_ROLE_RULE_OPTION {
                description    
                "none";
            }
            identity PORT_ROLE_RULE_OPTION_SAME_ROLE {
                base PORT_ROLE_RULE_OPTION;
                description    
                "The ports to which the rule applies must have role from the list in PortRole.";
            }
            identity PORT_ROLE_RULE_OPTION_DIFFERENT_ROLE {
                base PORT_ROLE_RULE_OPTION;
                description    
                "The ports to which the rule applies must not have a role from the list in PortRole.";
            }
            identity PORT_ROLE_RULE_OPTION_ANY_ROLE {
                base PORT_ROLE_RULE_OPTION;
                description    
                "The rule applies to any role of port.";
            }
            identity SIGNAL_PROPERTY_VALUE_RULE {
                description    
                "none";
            }
            identity SIGNAL_PROPERTY_VALUE_RULE_SAME_VALUE {
                base SIGNAL_PROPERTY_VALUE_RULE;
                description    
                "none";
            }
            identity SIGNAL_PROPERTY_VALUE_RULE_ANY_VALUE {
                base SIGNAL_PROPERTY_VALUE_RULE;
                description    
                "none";
            }
            identity PARTNER {
                description    
                "none";
            }
            identity PARTNER_FC {
                base PARTNER;
                description    
                "ForwardingConstruct.";
            }
            identity PARTNER_FD {
                base PARTNER;
                description    
                "ForwardingDomain.";
            }
            identity PARTNER_LINK {
                base PARTNER;
                description    
                "Link.";
            }
            identity PARTNER_CASC {
                base PARTNER;
                description    
                "ConfigurationAndSwitchController.";
            }
            identity PARTNER_CC {
                base PARTNER;
                description    
                "ControlConstruct.";
            }
            identity PARTNER_CD {
                base PARTNER;
                description    
                "ConstraintDomain.";
            }
            identity PARTNER_PC {
                base PARTNER;
                description    
                "ProcessingConstruct.";
            }
            identity PARTNER_PEER {
                base PARTNER;
                description    
                "LTP peer.";
            }
            identity PARTNER_CLIENT {
                base PARTNER;
                description    
                "LTP client.";
            }
            identity PARTNER_SERVER {
                base PARTNER;
                description    
                "LTP server.";
            }
            identity PARTNER_VIEW {
                base PARTNER;
                description    
                "LTP in other view.";
            }
            identity TASK_LIFECYCLE_STATE {
                description    
                "none";
            }
            identity TASK_LIFECYCLE_STATE_RUNNING {
                base TASK_LIFECYCLE_STATE;
                description    
                "The task is running.";
            }
            identity TASK_LIFECYCLE_STATE_PAUSED {
                base TASK_LIFECYCLE_STATE;
                description    
                "The task has been paused.";
            }
            identity TASK_LIFECYCLE_STATE_WAITING {
                base TASK_LIFECYCLE_STATE;
                description    
                "The task is waiting for input etc.";
            }
            identity TASK_LIFECYCLE_STATE_ABORTING {
                base TASK_LIFECYCLE_STATE;
                description    
                "The task is aborting.";
            }
            identity TASK_LIFECYCLE_STATE_COMPLETED {
                base TASK_LIFECYCLE_STATE;
                description    
                "The task has been completed successfully.";
            }
            identity TASK_LIFECYCLE_STATE_ABORTED {
                base TASK_LIFECYCLE_STATE;
                description    
                "The task has been aborted.";
            }
            identity TASK_LIFECYCLE_STATE_ATTEMPTING_ROLLBACK {
                base TASK_LIFECYCLE_STATE;
                description    
                "The task is attempting to return the controlled system to a previous state.";
            }
            identity TASK_LIFECYCLE_STATE_ROLLBACK_COMPLETE {
                base TASK_LIFECYCLE_STATE;
                description    
                "The task has completed a roll back action.";
            }
            identity TASK_LIFECYCLE_STATE_ABANDONING {
                base TASK_LIFECYCLE_STATE;
                description    
                "Task is abandoning.";
            }
            identity TASK_LIFECYCLE_STATE_ABANDONED {
                base TASK_LIFECYCLE_STATE;
                description    
                "The task has been abandoned and is no longer running.";
            }
            identity TASK_LIFECYCLE_STATE_FAILED {
                base TASK_LIFECYCLE_STATE;
                description    
                "The task has failed.";
            }
            identity TASK_LIFECYCLE_STATE_ARCHIVED {
                base TASK_LIFECYCLE_STATE;
                description    
                "The task has been archived (and is no longer running).";
            }
            identity PROGRESS_STATUS {
                description    
                "none";
            }
            identity PROGRESS_STATUS_COMPLETE {
                base PROGRESS_STATUS;
                description    
                "none";
            }
            identity PROGRESS_STATUS_IN_PROGRESS {
                base PROGRESS_STATUS;
                description    
                "none";
            }
            identity PROGRESS_STATUS_FAILED {
                base PROGRESS_STATUS;
                description    
                "none";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity.";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity.";
            }
            identity TERMINATION_DIRECTION_UNDEFINED_OR_UNKNOWN {
                base TERMINATION_DIRECTION;
                description    
                "Not a normal state. The system is unable to determine the correct value.";
            }
            identity TERMINATION_DIRECTION {
                description    
                "none";
            }
            identity TERMINATION_DIRECTION_BIDIRECTIONAL {
                base TERMINATION_DIRECTION;
                description    
                "A Termination with both SINK and SOURCE flows.";
            }
            identity TERMINATION_DIRECTION_SINK {
                base TERMINATION_DIRECTION;
                description    
                "The flow is up the layer stack from the server side to the client side. 
                    Considering an example of a Termination function within the termination entity, a SINK flow:
                    - will arrive at the base of the termination function (the server side) where it is essentially at an INPUT to the termination component
                    - then will be decoded and deconstructed 
                    - then relevant parts of the flow will be sent out of the termination function (the client side) where it is essentially at an OUTPUT from the termination component
                    A SINK termination is one that only supports a SINK flow.
                    A SINK termination can be bound to an OUTPUT Port of a Forwarding entity";
            }
            identity TERMINATION_DIRECTION_SOURCE {
                base TERMINATION_DIRECTION;
                description    
                "The flow is down the layer stack from the server side to the client side. 
                    Considering an example of a Termination function within the termination entity, a SOURCE flow:
                    - will arrive at the top of the termination function (the client side) where it is essentially at an INPUT to the termination component
                    - then will be assembled with various overheads etc. and will be coded 
                    - then coded form of the assembly of flow will be sent out of the termination function (the server side) where it is essentially at an OUTPUT from the termination component
                    A SOURCE termination is one that only supports a SOURCE flow.
                    A SOURCE termination can be bound to an INPUT Port of a Forwarding entity";
            }
            identity TERMINATION_DIRECTION_UNDEFINED_OR_UNKNOWN {
                base TERMINATION_DIRECTION;
                description    
                "Not a normal state. The system is unable to determine the correct value.";
            }
            identity ACTION_VERBS {
                description    
                "none";
            }
            identity ACTION_VERBS_CREATE_POST_ADD {
                base ACTION_VERBS;
                description    
                "none";
            }
            identity ACTION_VERBS_SET_UPDATE_PUT_MODIFY_WRITE_ADD {
                base ACTION_VERBS;
                description    
                "none";
            }
            identity ACTION_VERBS_GET_READ {
                base ACTION_VERBS;
                description    
                "none";
            }
            identity ACTION_VERBS_DELETE_REMOVE {
                base ACTION_VERBS;
                description    
                "none";
            }
            identity DIRECTION {
                description    
                "none";
            }
            identity DIRECTION_IN {
                base DIRECTION;
                description    
                "none";
            }
            identity DIRECTION_OUT {
                base DIRECTION;
                description    
                "none";
            }
            identity DIRECTION_BIDIRECTIONAL {
                base DIRECTION;
                description    
                "none";
            }
            identity ACTION_VERBS {
                description    
                "none";
            }
            identity ACTION_VERBS_CREATE_POST_ADD {
                base ACTION_VERBS;
                description    
                "Cause the addition of some structure.";
            }
            identity ACTION_VERBS_SET_UPDATE_PUT_MODIFY_WRITE_ADD {
                base ACTION_VERBS;
                description    
                "Cause the adjustment to some properties.";
            }
            identity ACTION_VERBS_GET_READ {
                base ACTION_VERBS;
                description    
                "Acquire information.";
            }
            identity ACTION_VERBS_DELETE_REMOVE {
                base ACTION_VERBS;
                description    
                "Eliminate some structure.";
            }
            identity ACTIVITY_DIRECTIVE {
                description    
                "none";
            }
            identity ACTIVITY_DIRECTIVE_STRUCTURE_IS_NOT {
                base ACTIVITY_DIRECTIVE;
                description    
                "The structure defined should not be present. No part should be present (within the stated degrees of precision.";
            }
            identity ACTIVITY_DIRECTIVE_NEW_STRUCTURE_AND_VALUES {
                base ACTIVITY_DIRECTIVE;
                description    
                "None of the structure stated is expected to be present, but is required.";
            }
            identity ACTIVITY_DIRECTIVE_INCREMENTAL_STRUCTURE_AND_VALUES {
                base ACTIVITY_DIRECTIVE;
                description    
                "The structure stated is an increment on what already exists.
                    Increment in this case may also be decrement.";
            }
            identity ACTIVITY_DIRECTIVE_ONLY_VALUES_IN_EXISTING_STRUCTURE {
                base ACTIVITY_DIRECTIVE;
                description    
                "Only values should be modified, no new structure should be created and no structure should be deleted.";
            }
            identity ACTIVITY_DIRECTIVE_DEFINED_BY_VERB {
                base ACTIVITY_DIRECTIVE;
                description    
                "A verb is provided to give guidance (such as Create).";
            }
            identity ACTION_EFFORT {
                description    
                "none";
            }
            identity ACTION_EFFORT_BEST_EFFORT {
                base ACTION_EFFORT;
                description    
                "none";
            }
            identity ACTION_EFFORT_EXACT_MATCH {
                base ACTION_EFFORT;
                description    
                "none";
            }
            identity PAUSE_RESUME_RULE {
                description    
                "none";
            }
            identity PAUSE_RESUME_RULE_NO_PAUSE_POSSIBLE {
                base PAUSE_RESUME_RULE;
                description    
                "none";
            }


}
