module core-model {
  namespace "urn:onf:params:xml:ns:yang:core-model";
  prefix core-model;

  organization
    "ONF (Open Networking Foundation) - Open Information Modeling & Tooling (OIMT)";
  contact
    "WG Web:   <https://wiki.opennetworking.org/pages/viewpage.action?pageId=259325962>
     WG List:  <mailto:information-modeling@opennetworking.org>
     WG Chair: Hing-Kam Lam
               <mailto:kamlam@fiberhome.com>
               Nigel Davis
               <mailto:ndavis@ciena.com>
     Editor:   Xing Zhao
               <mailto:zhaoxing@catr.cn>
               Martin Skorupski
               <mailto:martin.skorupski@highstreet-technologies.com>";
  description
    "This module contains a collection of YANG definitions for managing a single control component, such as wireless, RAN, IoT and other devices.";

  revision 2017-12-29 {
    description
      "Initial version";
    reference "ONF CoreModel 1.3";
  }

  identity port-direction {
    description
      "none";
  }

  identity port-direction-bidirectional {
    base port-direction;
    description
      "The Port has both an INPUT flow and an OUTPUT flow defined.";
  }

  identity port-direction-input {
    base port-direction;
    description
      "The Port only has definition for a flow into the Forwarding entity (i.e. an ingress flow).";
  }

  identity port-direction-output {
    base port-direction;
    description
      "The Port only has definition for a flow out of the Forwarding entity (i.e. an egress flow).";
  }

  identity port-direction-unidentified_or_unknown {
    base port-direction;
    description
      "Not a normal state. The system is unable to determine the correct value.";
  }

  identity port-direction-omnidirectional {
    base port-direction;
    description
      "none";
  }

  identity forwarding-direction {
    description
      "none";
  }

  identity forwarding-direction-bidirectional {
    base forwarding-direction;
    description
      "The Forwarding entity supports both BIDIRECTIONAL flows at all Ports (i.e. all Ports have both an INPUT flow and an OUTPUT flow defined).";
  }

  identity forwarding-direction-unidirectional {
    base forwarding-direction;
    description
      "The Forwarding entity has Ports that are either INPUT or OUTPUT. It has no BIDIRECTIONAL Ports.";
  }

  identity forwarding-direction-undefined_or_unknown {
    base forwarding-direction;
    description
      "Not a normal state. The system is unable to determine the correct value.";
  }

  identity forwarding-direction-omnidirectional {
    base forwarding-direction;
    description
      "none";
  }

  identity termination-direction {
    description
      "none";
  }

  identity termination-direction-bidirectional {
    base termination-direction;
    description
      "A Termination with both SINK and SOURCE flows.";
  }

  identity termination-direction-sink {
    base termination-direction;
    description
      "The flow is up the layer stack from the server side to the client side. 
       Considering an example of a Termination function within the termination entity, a SINK flow:
       - will arrive at the base of the termination function (the server side) where it is essentially at an INPUT to the termination component
       - then will be decoded and deconstructed 
       - then relevant parts of the flow will be sent out of the termination function (the client side) where it is essentially at an OUTPUT from the termination component
       A SINK termination is one that only supports a SINK flow.
       A SINK termination can be bound to an OUTPUT Port of a Forwarding entity";
  }

  identity termination-direction-source {
    base termination-direction;
    description
      "The flow is down the layer stack from the server side to the client side. 
       Considering an example of a Termination function within the termination entity, a SOURCE flow:
       - will arrive at the top of the termination function (the client side) where it is essentially at an INPUT to the termination component
       - then will be assembled with various overheads etc. and will be coded 
       - then coded form of the assembly of flow will be sent out of the termination function (the server side) where it is essentially at an OUTPUT from the termination component
       A SOURCE termination is one that only supports a SOURCE flow.
       A SOURCE termination can be bound to an INPUT Port of a Forwarding entity";
  }

  identity termination-direction-undefined_or_unknown {
    base termination-direction;
    description
      "Not a normal state. The system is unable to determine the correct value.";
  }

  identity termination-state {
    description
      "none";
  }

  identity termination-state-lp_can_never_terminate {
    base termination-state;
    description
      "A non-flexible case that can never be terminated.";
  }

  identity termination-state-lp_not_terminated {
    base termination-state;
    description
      "A flexible termination that can terminate but is currently not terminated.";
  }

  identity termination-state-terminated_server_to_client_flow {
    base termination-state;
    description
      "A flexible termination that is currently terminated for server to client flow only.";
  }

  identity termination-state-terminated_client_to_server_flow {
    base termination-state;
    description
      "A flexible termination that is currently terminated for client to server flow only.";
  }

  identity termination-state-terminated_bidirectional {
    base termination-state;
    description
      "A flexible termination that is currently terminated in both directions of flow.";
  }

  identity termination-state-lp_permenantly_terminated {
    base termination-state;
    description
      "A non-flexible termination that is always terminated (in both directions of flow for a bidirectional case and in the one direction of flow for both unidirectional cases).";
  }

  identity termination-state-termination_state_unknown {
    base termination-state;
    description
      "There TerminationState cannot be determined.";
  }

  identity protection-reason {
    description
      "none";
  }

  identity protection-reason-wait_to_revert {
    base protection-reason;
    description
      "The resource is selected as control is waiting to restore to a preferred resource.";
  }

  identity protection-reason-signal_degrade {
    base protection-reason;
    description
      "The resource is selected as the best preferred resource is in signal degrade.";
  }

  identity protection-reason-signal_fail {
    base protection-reason;
    description
      "The resource is selected as the best preferred resource is in signal fail.";
  }

  identity route-selection-reason {
    description
      "none";
  }

  identity switch-control {
    description
      "none";
  }

  identity switch-control-normal {
    base switch-control;
    description
      "No administrative control applied to the switch.";
  }

  identity switch-control-manual {
    base switch-control;
    description
      "Resource temporarily chosen by control configuration where the resource is not the preferred resource.
       Preferred resource has highest priority.
       Temporarily overrides reversion.
       If this resource fails, it will switch to best available resource. 
       If resource selected is shared and another FC requires the resource, then the selection control will change to Normal and switch to best available based upon normal rules.
       Cannot manually switch a Forced switch, cannot remove a forced switch, cannot switch to a locked out item and will be rejected if the protection process is deactivated by being Freeze = true).
       A manual switch/route that is selecting an FcPort, LTP, FC, Link or Route that is subsequently set to LOCK_OUT will have the manual removed (changed to NORMAL) and will switch away from the  FcPort with LOCK_OUT to best available based upon normal rules.
       A manual switch that is selecting an FcPort that is subsequently selected by a Forced switch will be restored to normal operation and the manual will be removed.
       A manual switch/route that is selecting an FcPort, LTP, FC, Link or Route that is subsequently manual selected by another switch/route  will have the manual removed and will switch away from the FcPort.
       Can be returned to NORMAL by configuration action.";
  }

  identity switch-control-forced {
    base switch-control;
    description
      "Resource temporarily chosen by control configuration where the resource is not the preferred resource.
       Preferred resource has highest priority.
       Temporarily overrides reversion.
       If this resource fails it will NOT switch. 
       If resource selected is shared and another FC requires the resource through a FORCE on that FC and the FC is of a higher FcPriority then the selection control on this FC will change to NORMAL and switch to best available based upon normal rules.
       If the resource selected is then set to LOCK_OUT then the selection control will change to NORMAL and switch to best available based upon normal rules.
       Can be returned to NORMAL by configuration action.";
  }

  identity switch-state-reason {
    description
      "none";
  }

  identity reversion-mode {
    description
      "none";
  }

  identity reversion-mode-revertive {
    base reversion-mode;
    description
      "An FC switched to a lower priority (non-preferred) resource will revert to a higher priority (preferred) resource when that recovers (potentially after some hold-off time).";
  }

  identity reversion-mode-non-revertive {
    base reversion-mode;
    description
      "An FC switched to a lower priority (non-preferred) resource will not revert to a higher priority (preferred) resource when that recovers.";
  }

  identity resilience-control {
    description
      "none";
  }

  identity resilience-control-quiescent {
    base resilience-control;
    description
      "none";
  }

  identity resilience-control-restoring {
    base resilience-control;
    description
      "none";
  }

  identity resilience-control-recovery_failed {
    base resilience-control;
    description
      "none";
  }

  identity resilience-control-unknown {
    base resilience-control;
    description
      "none";
  }

  identity run-mode {
    description
      "none";
  }

  identity run-mode-free_run {
    base run-mode;
    description
      "The ckock is not synchronized to another clock.";
  }

  identity run-mode-locked {
    base run-mode;
    description
      "The clock is synchronised to another clock.";
  }

  identity run-mode-hold_over {
    base run-mode;
    description
      "The clock was previously synchonised to another clock but that timing input has been lost.
       The clock is set to the last known synchronization.";
  }

  identity operational-state {
    description
      "none";
  }

  identity operational-state-disabled {
    base operational-state;
    description
      "The resource is unable to meet the SLA of the user of the resource. 
       If no (explicit) SLA is defined the resource is disabled if it is totally inoperable and unable to provide service to the user.";
  }

  identity operational-state-enabled {
    base operational-state;
    description
      "The resource is partially or fully operable and available for use.";
  }

  identity administrative-state {
    description
      "none";
  }

  identity administrative-state-locked {
    base administrative-state;
    description
      "Users are administratively prohibited from making use of the resource.";
  }

  identity administrative-state-unlocked {
    base administrative-state;
    description
      "Users are allowed to use the resource.";
  }

  identity administrative-state-shutting_down {
    base administrative-state;
    description
      "The entity is administratively restricted to existing instances of use only. There may be specific actions to remove existing uses. No new instances of use can be enabled.
       The resource automatically transitions to “locked” when the last user quits. 
       The administrative state is not visible in the client context. 
       The lifecycle state “pending removal” should be used to indicate to the client that the provider intends to remove the resource.";
  }

  identity administrative-control {
    description
      "none";
  }

  identity administrative-control-unlock {
    base administrative-control;
    description
      "The intention is for the entity to become unlocked.
       The entity may already be UNLOCKED.";
  }

  identity administrative-control-lock_passive {
    base administrative-control;
    description
      "The intention is for the entity to become locked but no effort is expected to move to the Locked state (the state will be achieved once all users stop using the resource). 
       The entity may be LOCKED.";
  }

  identity administrative-control-lock_active {
    base administrative-control;
    description
      "The intention is for the entity to become locked and it is expected that effort will be made to move to the Locked state (users will be actively removed). 
       The entity may already be LOCKED.";
  }

  identity administrative-control-lock_immediate {
    base administrative-control;
    description
      "The intention is for the entity to become locked and it is expected to move to the Locked state immediately (users will be force removed). 
       The entity may already be LOCKED.";
  }

  identity administrative-control-quiescent {
    base administrative-control;
    description
      "The administrative state is at a stable value (LOCKED/UNLOCKED) and no action is being taken.";
  }

  identity lifecycle-state {
    description
      "none";
  }

  identity lifecycle-state-planned {
    base lifecycle-state;
    description
      "The resource is planned but is not present in the network.
       Should include a 'time' when the resources are expected to be installed.";
  }

  identity lifecycle-state-potential_available {
    base lifecycle-state;
    description
      "The supporting resources are present in the network but are shared with other clients; or require further configuration before they can be used; or both.
       (1) When a potential resource is configured and allocated to a client it is moved to the INSTALLED state for that client.
       (2) If the potential resource has been consumed (e.g. allocated to another client) it is moved to the POTENTIAL BUSY state for all other clients.";
  }

  identity lifecycle-state-potential_busy {
    base lifecycle-state;
    description
      "The supporting resources are present in the network but have been allocated to other clients.";
  }

  identity lifecycle-state-installed {
    base lifecycle-state;
    description
      "The resource is present in the network and is capable of providing the service.";
  }

  identity lifecycle-state-pending_removal {
    base lifecycle-state;
    description
      "The resource has been marked for removal.  Should include a “time” when the resources are expected to be removed.";
  }

  identity action-verbs {
    description
      "none";
  }

  identity action-verbs-create_post_add {
    base action-verbs;
    description
      "none";
  }

  identity action-verbs-set_update_put_modify_write_add {
    base action-verbs;
    description
      "none";
  }

  identity action-verbs-get_read {
    base action-verbs;
    description
      "none";
  }

  identity action-verbs-delete_remove {
    base action-verbs;
    description
      "none";
  }

  identity activity-directive {
    description
      "none";
  }

  identity activity-directive-structure_is_not {
    base activity-directive;
    description
      "none";
  }

  identity activity-directive-new_structure_and_values {
    base activity-directive;
    description
      "none";
  }

  identity activity-directive-incremental_structure_and_values {
    base activity-directive;
    description
      "none";
  }

  identity activity-directive-only_values_in_existing_structure {
    base activity-directive;
    description
      "none";
  }

  identity activity-directive-defined_by_verb {
    base activity-directive;
    description
      "none";
  }

  identity action-effort {
    description
      "none";
  }

  identity action-effort-best_effort {
    base action-effort;
    description
      "none";
  }

  identity action-effort-exact_match {
    base action-effort;
    description
      "none";
  }

  identity pause-resume-rule {
    description
      "none";
  }

  identity NO_PAUSE_POSSIBLE {
    base pause-resume-rule;
    description
      "none";
  }

  identity connector-and-pin-orientation {
    description
      "none";
  }

  identity connector-and-pin-orientation-male {
    base connector-and-pin-orientation;
    description
      "The connecting elements are dominantly protrusions.";
  }

  identity connector-and-pin-orientation-female {
    base connector-and-pin-orientation;
    description
      "The connecting elements are dominantly indentations.";
  }

  identity connector-and-pin-orientation-symmetric_neutral {
    base connector-and-pin-orientation;
    description
      "The pin (and housing) orientation combination is such that it is symmetric so a connector is compatible with itself.
       The connecting element may be a surface rather than protrusions or indentations.";
  }

  identity equipment-category {
    description
      "none";
  }

  identity equipment-category-subrack {
    base equipment-category;
    description
      "An assembly with holders designed to accommodate CIRCUIT_PACKs. 
       The assembly is designed to be mounted in a RACK.";
  }

  identity equipment-category-circuit_pack {
    base equipment-category;
    description
      "An assembly with connectors compatible with those in a holder.
       The assembly is designed to be mounted in a holder (SLOT) of a SUBRACK.
       May also support holders (SLOTs) for SMALL_FORMFACTOR_PLUGGABLEs.";
  }

  identity equipment-category-small_formfactor_pluggable {
    base equipment-category;
    description
      "A small assembly (compared to a CIRCUIT_PACK) with connectors compatible with those in a holder.
       The assembly is designed to be mounted in a holder (SLOT) of a CIRCUIT_PACK or STAND_ALONE_UNIT.";
  }

  identity equipment-category-stand_alone_unit {
    base equipment-category;
    description
      "An assembly with connectors for cabling and potentially with holders.
       The assembly is designed to be mounted in a freeform environment (on a table or simple mechanical cabinet).
       May support holders (SLOTs) for CIRCUIT_PACKs or for SMALL_FORMFACTOR_PLUGGABLEs.";
  }

  identity equipment-category-rack {
    base equipment-category;
    description
      "A mechanical assembly with cabling and predefined mounting points for particular SUBRACK types.
       The assembly is designed to be mounted on the floor in a row with other RACKs.";
  }

  identity holder-category {
    description
      "none";
  }

  identity SLOT {
    base holder-category;
    description
      "A guided holder with fixed connectors.
       The guided holder is designed to take a particular form of CIRCUIT_PACK or SMALL_FORMFACTOR_PLUGGABLE";
  }

  identity forwarding-rule {
    description
      "none";
  }

  identity forwarding-rule-cannot_forward_across_fd_link {
    base forwarding-rule;
    description
      "LTPs referenced by the FD (or indirectly by the Link between FDs) cannot have FCs created between them.
       This rule overrides all others.";
  }

  identity forwarding-rule-must_forward_across_fd_link {
    base forwarding-rule;
    description
      "LTPs referenced by the FD (or indirectly by the Link between FDs) MUST have FCs created between them.
       This rule overrides all others except the CANNOT_FORWARD rule.";
  }

  identity forwarding-rule-may_forward_across_fd_link {
    base forwarding-rule;
    description
      "LTPs referenced by the FD (or indirectly by the Link between FDs) may have FCs created between them.
       FCs may not be created between points that are not related by this rule either directly in an FD or indirectly via a Link linking two or more FDs.
       For a Link points in an FD at one end of the Link can be connected to points in an FD at an other end of the Link.";
  }

  identity forwarding-rule-null_forwarding_rule {
    base forwarding-rule;
    description
      "none";
  }

  identity rule-type {
    description
      "none";
  }

  identity rule-type-forwarding {
    base rule-type;
    description
      "The rule relates to creation of FCs.";
  }

  identity rule-type-cost {
    base rule-type;
    description
      "The rule relates to forwarding cost.";
  }

  identity rule-type-risk {
    base rule-type;
    description
      "The rule relates to forwarding risk.";
  }

  identity rule-type-capacity {
    base rule-type;
    description
      "none";
  }

  identity port-role-rule {
    description
      "none";
  }

  identity port-role-rule-same_role {
    base port-role-rule;
    description
      "none";
  }

  identity port-role-rule-different_role {
    base port-role-rule;
    description
      "none";
  }

  identity port-role-rule-any_role {
    base port-role-rule;
    description
      "none";
  }

  identity signal-property-value-rule {
    description
      "none";
  }

  identity signal-property-value-rule-same_value {
    base signal-property-value-rule;
    description
      "none";
  }

  identity signal-property-value-rule-any_value {
    base signal-property-value-rule;
    description
      "none";
  }

  grouping cost-characteristics-g {
    leaf cost-name {
      type string;
      description
        "The cost characteristic will related to some aspect of the ForwardingEntity (e.g. $ cost, routing weight). This aspect will be conveyed by the costName.";
    }
    leaf cost-value {
      type string;
      description
        "The specific cost.";
    }
    leaf cost-algorithm {
      type to-be-defined;
      description
        "The cost may vary based upon some properties of the ForwardingEntity. The rules for the variation are conveyed by the costAlgorithm.";
    }
    description
      "The information for a particular cost characteristic.";
  }

  grouping risk-characteristic-g {
    leaf risk-characteristic-name {
      type string;
      description
        "The name of the risk characteristic. The characteristic may be related to a specific degree of closeness. 
         For example, a particular characteristic may apply to failures that are localized (e.g. to one side of a road) where as another characteristic may relate to failures that have a broader impact (e.g. both sides of a road that crosses a bridge).
         Depending upon the importance of the traffic being routed different risk characteristics will be evaluated.";
    }
    leaf-list risk-identifier {
      type string;
      min-elements 1;
      description
        "A list of the identifiers of each physical/geographic unit (with the specific risk characteristic) that is related to a segment of the ForwardingEntity.";
    }
    description
      "The information for a particular risk characteristic where there is a list of risk identifiers related to that characteristic.";
  }

  grouping capacity-g {
    leaf total-size {
      type string;
      description
        "Total capacity of the ForwardingEntity in Mbits/s";
    }
    leaf number-of-client-instances {
      type string;
      description
        "Where there is some limit to the number of client (e.g. in a channelized case).";
    }
    leaf maximum-client-size {
      type string;
      description
        "Where a client is of variable capacity but due to some underlying realization the maximum size of the client is smaller than the totalSize.";
    }
    leaf numbering-range {
      type string;
      description
        "Method for identifying units of capacity via some numbering scheme.";
    }
    description
      "Information on capacity of a particular ForwardingEntity.";
  }

  grouping validation-mechanism-g {
    leaf validation-mechanism {
      type string;
      description
        "Name of mechanism used to validate adjacency.";
    }
    leaf layer-protocol-adjacency-validated {
      type string;
      description
        "State of validation.";
    }
    leaf validation-robustness {
      type string;
      description
        "Quality of validation (i.e. how likely is the stated validation to be invalid).";
    }
    description
      "Identifies the validation mechanism and describes the characteristics of that mechanism.";
  }

  grouping queuing-latency-g {
    leaf traffic-property {
      type string;
      description
        "The identifier of the specific traffic property to which the queuing latency applies.";
    }
    leaf latency-for-traffic-with-property {
      type string;
      description
        "The specific queuing latency for the traffic property.";
    }
    description
      "Provides information on latency characteristic for a particular stated trafficProperty.";
  }

  typedef protection-reason {
    type identityref {
      base protection-reason;
    }
    description
      "The cause of the current protection state.";
  }

  typedef switch-control {
    type identityref {
      base switch-control;
    }
    description
      "none";
  }

  typedef reversion-mode {
    type identityref {
      base reversion-mode;
    }
    description
      "The reversion mode associated with protection.";
  }

  grouping global-pac-g {
    uses global-class-g;
    description
      "Provides the properties of a GlobalClass via composition.";
  }

  grouping local-pac-g {
    uses local-class-g;
    description
      "Provides the properties of a LocalClass via composition.";
  }

  typedef protection-type {
    type string;
    description
      "Identifies the type of protection of an FcSwitch.";
  }

  typedef resilience-control {
    type identityref {
      base resilience-control;
    }
    description
      "none";
  }

  typedef run-mode {
    type identityref {
      base run-mode;
    }
    description
      "none";
  }

  typedef layer-protocol-name {
    type string;
    description
      "Provides a controlled list of layer protocol names and indicates the naming authority.
       Note that it is expected that attributes will be added to this structure to convey the naming authority name, the name of the layer protocol using a human readable string and any particular standard reference.
       Layer protocol names include:
       -    Layer 1 (L1): OTU, ODU
       -    Layer 2 (L2): Carrier Grade Ethernet (ETY, ETH), MPLS-TP (MT)
      ";
  }

  typedef port-role {
    type string;
    description
      "The role of a port in the context of the function of the forwarding entity that it bounds.";
  }

  typedef port-direction {
    type identityref {
      base port-direction;
    }
    description
      "The orientation of flow at the Port of a Forwarding entity.";
  }

  typedef forwarding-direction {
    type identityref {
      base forwarding-direction;
    }
    description
      "The directionality of a Forwarding entity.";
  }

  typedef termination-direction {
    type identityref {
      base termination-direction;
    }
    description
      "The directionality of a termination entity.";
  }

  typedef termination-state {
    type identityref {
      base termination-state;
    }
    description
      "Provides support for the range of behaviors and specific states that an LP can take with respect to termination of the signal.
       Indicates to what degree the LayerTermination is terminated.";
  }

  grouping transfer-cost-pac-g {
    list cost-characteristic {
      key "cost-name";
      min-elements 1;
      uses cost-characteristics-g;
      description
        "The list of costs where each cost relates to some aspect of the ForwardingEntity.";
    }
    description
      "The cost characteristics of a ForwardingEntity not necessarily correlated to the cost of the underlying physical realization. 
       They may be quite specific to the individual ForwardingEntity (e.g. opportunity cost) and relates to layer capacity
       There may be many perspectives from which cost may be considered for a particular ForwardingEntity and hence many specific costs and potentially cost algorithms. 
       Using an entity will incur a cost. ";
  }

  grouping risk-parameter-pac-g {
    list risk-characteristic {
      key "risk-characteristic-name";
      min-elements 1;
      uses risk-characteristic-g;
      description
        "A list of risk characteristics for consideration in an analysis of shared risk. Each element of the list represents a specific risk consideration.";
    }
    description
      "The risk characteristics of a ForwardingEntity come directly from the underlying physical realization. 
       The risk characteristics propagate from the physical realization to the client and from the server layer to the client layer; this propagation may be modified by protection.
       A ForwardingEntity may suffer degradation or failure as a result of a problem in a part of the underlying realization.
       The realization can be partitioned into segments which have some relevant common failure modes.
       There is a risk of failure/degradation of each segment of the underlying realization.
       Each segment is a part of a larger physical/geographical unit that behaves as one with respect to failure (i.e. a failure will have a high probability of impacting the whole unit (e.g. all cables in the same duct).
       Disruptions to that larger physical/geographical unit will impact (cause failure/errors to) all ForwardingEntities that use any part of that larger physical/geographical entity.
       Any ForwardingEntity that uses any part of that larger physical/geographical unit will suffer impact and hence each ForwardingEntity shares risk.
       The identifier of each physical/geographical unit that is involved in the realization of each segment of a ForwardingEntity can be listed in the RiskParameter_Pac of that ForwardingEntity.
       A segment has one or more risk characteristic.
       Shared risk between two ForwardingEntities compromises the integrity of any solution that use one of those ForwardingEntity as a backup for the other.
       Where two ForwardingEntities have a common risk characteristic they have an elevated probability of failing simultaneously compared to two ForwardingEntities that do not share risk characteristics.";
  }

  grouping layer-protocol-transition-pac-g {
    leaf-list transitioned-layer-protocol {
      type string;
      min-elements 2;
      description
        "Provides the ordered structure of layer protocol transitions encapsulated in the ForwardingEntity. 
         The list starts with the client side as the first entry and includes all layer-protocol names (hence the smallest number is 2 as otherwise the Link is not transitional). 
         The ordering relates also to the LinkPort role (which emphasizes the orientation). 
         Where the transitional link is multi-ported and layer asymmetric the list includes the superset of layer-protocol names. 
         Transitional links can only be applied where the transition for each port is such that all transitions between any ports are subsequences of the list. 
         The specific subsequence is determined by the LayerProtocols of the LTP associated with the LinkPort and the role of the LinkPort.";
    }
    leaf-list ltp {
      type leafref {
        path "/core-model:logical-termination-point/core-model:uuid";
      }
      min-elements 1;
      description
        "Lists the LTPs that define the layer protocol transition of the transitional link.";
    }
    uses global-class-g;
    description
      "The transition characteristics are relevant for a Link that is formed by abstracting one or more LTPs (in a stack) to focus on the flow and deemphasize the protocol transformation. 
       This abstraction is relevant when considering multi-layer routing. 
       The layer protocols of the LTP and the order of their application to the signal is still relevant and needs to be accounted for (this is derived from the LTP spec details).
       This Pac provides the relevant abstractions of the LTPs and provides the necessary association to the LTPs involved.
       Links that include details in this Pac are often referred to as Transitional Links.";
  }

  grouping transfer-timing-pac-g {
    leaf fixed-latency-characteristic {
      type string;
      description
        "A ForwardingEntity suffers delay caused by the realization of the servers (e.g. distance related; FEC encoding etc.) along with some client specific processing. This is the total average latency effect of the ForwardingEntity.";
    }
    leaf jitter-characteristic {
      if-feature "_QcR4IKNVEeS9Obpdy8FCjA";
      type string;
      description
        "High frequency deviation from true periodicity of a signal and therefore a small high rate of change of transfer latency.
         Applies to TDM systems (and not packet).";
    }
    leaf wander-characteristic {
      if-feature "_ZID8gKNVEeS9Obpdy8FCjA";
      type string;
      description
        "Low frequency deviation from true periodicity of a signal and therefore a small low rate of change of transfer latency.
         Applies to TDM systems (and not packet).";
    }
    list queuing-latency-characteristic {
      if-feature "_4ySjcK3mEeSXJ6XI-2nsRw";
      key "traffic-property";
      uses queuing-latency-g;
      description
        "The effect on the latency of a queuing process. This only has significant effect for packet based systems and has a complex characteristic.";
    }
    description
      "A ForwardingEntity will suffer effects from the underlying physical realization related to the timing of the information passed by the ForwardingEntity.";
  }

  grouping transfer-integrity-pac-g {
    leaf error-characteristic {
      if-feature "_VIujsKNWEeS9Obpdy8FCjA";
      type string;
      description
        "Describes the degree to which the signal propagated can be errored. 
         Applies to TDM systems as the errored signal will be propagated and not packet as errored packets will be discarded.";
    }
    leaf loss-characteristic {
      if-feature "_ZuWrAKNWEeS9Obpdy8FCjA";
      type string;
      description
        "Describes the acceptable characteristic of lost packets where loss may result from discard due to errors or overflow.
         Applies to packet systems and not TDM (as for TDM errored signals are propagated unless grossly errored and overflow/underflow turns into timing slips).";
    }
    leaf repeat-delivery-characteristic {
      if-feature "_bVjSUKNWEeS9Obpdy8FCjA";
      type string;
      description
        "Primarily applies to packet systems where a packet may be delivered more than once (in fault recovery for example). 
         It can also apply to TDM where several frames may be received twice due to switching in a system with a large differential propagation delay.";
    }
    leaf delivery-order-characteristic {
      if-feature "_hGi0wL7aEeSdssyZX-p90g";
      type string;
      description
        "Describes the degree to which packets will be delivered out of sequence.
         Does not apply to TDM as the TDM protocols maintain strict order.";
    }
    leaf unavailable-time-characteristic {
      type string;
      description
        "Describes the duration for which there may be no valid signal propagated.";
    }
    leaf server-integrity-process-characteristic {
      if-feature "_piS5EL7aEeSdssyZX-p90g";
      type string;
      description
        "Describes the effect of any server integrity enhancement process on the characteristics of the ForwardingEntity.";
    }
    description
      "Transfer integrity characteristic covers expected/specified/acceptable characteristic of degradation of the transferred signal.
       It includes all aspects of possible degradation of signal content as well as any damage of any form to the total ForwardingEntity and to the carried signals.
       Note that the statement is of total impact to the ForwardingEntity so any partial usage of the ForwardingEntity (e.g. a signal that does not use full capacity) will only suffer its portion of the impact.";
  }

  grouping transfer-capacity-pac-g {
    container total-potential-capacity {
      uses capacity-g;
      description
        "An optimistic view of the capacity of the ForwardingEntity assuming that any shared capacity is available to be taken.";
    }
    container available-capacity {
      uses capacity-g;
      description
        "Capacity available to be assigned.";
    }
    list capacity-assigned-to-user-view {
      key "total-size";
      uses capacity-g;
      description
        "Capacity already assigned.";
    }
    leaf capacity-interaction-algorithm {
      type string;
      description
        "A reference to an algorithm that describes how various chunks of allocated capacity interact (e.g. when shared).";
    }
    description
      "The ForwardingEntity derives capacity from the underlying realization. 
       A ForwardingEntity may be an abstraction and virtualization of a subset of the underlying capability offered in a view or may be directly reflecting the underlying realization.
       A ForwardingEntity may be directly used in the view or may be assigned to another view for use.
       The clients supported by a multi-layer ForwardingEntity may interact such that the resources used by one client may impact those available to another. This is derived from the LTP spec details.
       Represents the capacity available to user (client) along with client interaction and usage. 
       A ForwardingEntity may reflect one or more client protocols and one or more members for each profile.";
  }

  grouping forwarding-entity-g {
    container risk-parameter-pac {
      if-feature "_eH6McJ2IEeSQBuaNnP_LbA";
      uses risk-parameter-pac-g;
      description
        "none";
    }
    container transfer-cost-pac {
      if-feature "_ny1ZoJ2IEeSQBuaNnP_LbA";
      uses transfer-cost-pac-g;
      description
        "none";
    }
    container transfer-timing-pac {
      if-feature "_woOF8J2IEeSQBuaNnP_LbA";
      uses transfer-timing-pac-g;
      description
        "none";
    }
    container transfer-capacity-pac {
      if-feature "_CEGuAJ2JEeSQBuaNnP_LbA";
      uses transfer-capacity-pac-g;
      description
        "none";
    }
    container transfer-integrity-pac {
      if-feature "_QLzBcJ2JEeSQBuaNnP_LbA";
      uses transfer-integrity-pac-g;
      description
        "none";
    }
    container validation-pac {
      if-feature "_h8bfkJ2LEeSQBuaNnP_LbA";
      uses validation-pac-g;
      description
        "none";
    }
    list layer-transition-pac {
      if-feature "_f9upIJ2JEeSQBuaNnP_LbA";
      key "uuid";
      uses layer-protocol-transition-pac-g;
      description
        "none";
    }
    description
      "A ForwardingEntity is an abstract representation of the emergent effect of the combined functioning of an arrangement of components (running hardware, software running on hardware etc.). 
       The effect can be considered as the realization of the potential for apparent communication adjacency for entities that are bound to the terminations at the boundary of the ForwardingEntity.
       The ForwardingEntity enables the creation of constrained forwarding to achieve the apparent adjacency.
       The apparent adjacency has intended performance degraded from perfect adjacency and a statement of that degradation is conveyed via the attributes of the packages associated with this class.";
  }

  grouping validation-pac-g {
    list validation-mechanism {
      key "validation-mechanism";
      min-elements 1;
      uses validation-mechanism-g;
      description
        "Provides details of the specific validation mechanism(s) used to confirm the presence of an intended ForwardingEntity.";
    }
    description
      "Validation covers the various adjacency discovery and reachability verification protocols. Also may cover Information source and degree of integrity.";
  }

  feature _QcR4IKNVEeS9Obpdy8FCjA {
    description
      "Present if jitterCharacteristic information is relevant to usage and statement can be made that applies equally to all flows that can be supported by the ForwardingEntity.
       Note that if jitterCharacteristic is relevant but consistent statement cannot be made then the ForwardingEntity should be described in terms of subordinate parts against which coherent statements can be made.
       Note that this only applies to TDM.";
  }

  feature _ZID8gKNVEeS9Obpdy8FCjA {
    description
      "Present if wanderCharacteristic information is relevant to usage and statement can be made that applies equally to all flows that can be supported by the ForwardingEntity.
       Note that if wanderCharacteristic is relevant but consistent statement cannot be made then the ForwardingEntity should be described in terms of subordinate parts against which coherent statements can be made.
       Note that this only applies to TDM.";
  }

  feature _4ySjcK3mEeSXJ6XI-2nsRw {
    description
      "Present if queuingLatencyCharacteristic information is relevant to usage and statement can be made that applies equally to all flows that can be supported by the ForwardingEntity.
       There may be more than one instance if the queuing behavior depends upon traffic properties.
       Note that if queuingLatencyCharacteristic is relevant but consistent statement cannot be made then the ForwardingEntity should be described in terms of subordinate parts against which coherent statements can be made.
       Note that this only applies to packet system.";
  }

  feature _VIujsKNWEeS9Obpdy8FCjA {
    description
      "Present if errorCharacteristic information is relevant to usage and statement can be made that applies equally to all flows that can be supported by the ForwardingEntity.
       Note that if errorCharacteristic is relevant but consistent statement cannot be made then the ForwardingEntity should be described in terms of subordinate parts against which coherent statements can be made.
       Note that this only applies to TDM.";
  }

  feature _ZuWrAKNWEeS9Obpdy8FCjA {
    description
      "Present if lossCharacteristic information is relevant to usage and statement can be made that applies equally to all flows that can be supported by the ForwardingEntity.
       Note that if lossCharacteristic is relevant but consistent statement cannot be made then the ForwardingEntity should be described in terms of subordinate parts against which coherent statements can be made.
       Note that this only applies to packet systems.";
  }

  feature _bVjSUKNWEeS9Obpdy8FCjA {
    description
      "Present if repeatDeliveryCharacteristic information is relevant to usage and statement can be made that applies equally to all flows that can be supported by the ForwardingEntity.
       Note that if repeatDeliveryCharacteristic is relevant but consistent statement cannot be made then the ForwardingEntity should be described in terms of subordinate parts against which coherent statements can be made.
       Note that this primarily applies to packet systems where a packet may be delivered more than once (in fault recovery for example). 
       Note that it can also apply to TDM where several frames may  be received twice due to switching in a system with a large differential propagation delay.";
  }

  feature _hGi0wL7aEeSdssyZX-p90g {
    description
      "Present if deliveryOrderCharacteristic information is relevant to usage and statement can be made that applies equally to all flows that can be supported by the ForwardingEntity.
       Note that if deliveryOrderCharacteristic is relevant but consistent statement cannot be made then the ForwardingEntity should be described in terms of subordinate parts against which coherent statements can be made.
       Note that this only applies to packet systems.
      ";
  }

  feature _piS5EL7aEeSdssyZX-p90g {
    description
      "Present if serverIntegrityProcessCharacteristic information is relevant to usage and statement can be made that applies equally to all flows that can be supported by the ForwardingEntity.
       Note that if serverIntegrityProcessCharacteristic is relevant but consistent statement cannot be made then the ForwardingEntity should be described in terms of subordinate parts against which coherent statements can be made.
       Note that this only applies where the server has some error recovery mechanism alters the characteristics of the link from a normal distribution.";
  }

  feature _eH6McJ2IEeSQBuaNnP_LbA {
    description
      "Present if risk information is relevant to usage and statement can be made that applies equally to all flows that can be supported by the ForwardingEntity.
       Note that if risk is relevant but consistent statement cannot be made then the ForwardingEntity should be described in terms of subordinate parts against which coherent statements can be made.";
  }

  feature _ny1ZoJ2IEeSQBuaNnP_LbA {
    description
      "Present if cost information is relevant to usage and statement can be made that applies equally to all flows that can be supported by the ForwardingEntity.
       Note that if cost is relevant but consistent statement cannot be made then the ForwardingEntity should be described in terms of subordinate parts against which coherent statements can be made.";
  }

  feature _woOF8J2IEeSQBuaNnP_LbA {
    description
      "Present if transfer timing information is relevant to usage and statement can be made that applies equally to all flows that can be supported by the ForwardingEntity.
       Note that if transfer timing is relevant but consistent statement cannot be made then the ForwardingEntity should be described in terms of subordinate parts against which coherent statements can be made.";
  }

  feature _CEGuAJ2JEeSQBuaNnP_LbA {
    description
      "Present if transfer capacity information is relevant to usage and statement can be made that applies equally to all flows that can be supported by the ForwardingEntity.
       Note that if transfer capacity is relevant but consistent statement cannot be made then the ForwardingEntity should be described in terms of subordinate parts against which coherent statements can be made.";
  }

  feature _QLzBcJ2JEeSQBuaNnP_LbA {
    description
      "Present if transfer integrity information is relevant to usage and statement can be made that applies equally to all flows that can be supported by the ForwardingEntity.
       Note that if transfer integrity is relevant but consistent statement cannot be made then the ForwardingEntity should be described in terms of subordinate parts against which coherent statements can be made.";
  }

  feature _h8bfkJ2LEeSQBuaNnP_LbA {
    description
      "Present if validation information is relevant to usage and statement can be made that applies equally to all flows that can be supported by the ForwardingEntity.
       Note that if validation is relevant but consistent statement cannot be made then the ForwardingEntity should be described in terms of subordinate parts against which coherent statements can be made.
       Note that validation may not be possible for the specific layer protocol or in the particular case.";
  }

  feature _f9upIJ2JEeSQBuaNnP_LbA {
    description
      "Present if layer transition information is relevant to usage and statement can be made that applies equally to all flows that can be supported by the ForwardingEntity.
       Note that if layer transition is relevant but consistent statement cannot be made then the ForwardingEntity should be described in terms of subordinate parts against which coherent statements can be made.
       Note that layer transition occurs in a limited number of cases.";
  }

  grouping configuration-and-switch-control-g {
    leaf switch-rule {
      type to-be-defined;
      description
        "A sketch of the presence of complex rules governing the switch behavior.";
    }
    leaf-list fc-switch {
      type leafref {
        path "/core-model:fc-switch/core-model:local-id";
      }
      description
        "The switch being controlled.";
    }
    leaf control-parameters {
      type leafref {
        path "/core-model:control-parameters/core-model:uuid";
      }
      description
        "The control parameters to be applied if local parameters are used rather than profiles.";
    }
    leaf-list profile-proxy {
      type leafref {
        path "/core-model:profile-proxy/core-model:profile-proxy-mode";
      }
      description
        "Applied profiles.";
    }
    container local-pac {
      uses local-pac-g;
      description
        "none";
    }
    container global-pac {
      uses global-pac-g;
      description
        "none";
    }
    leaf is-frozen {
      type boolean;
      description
        "Temporarily prevents any switch action to be taken and, as such, freezes the current state. 
         Until the freeze is cleared, additional near-end external commands are rejected and fault condition changes and received APS messages are ignored.
         All administrative controls of any aspect of protection are rejected.";
    }
    leaf is-coordinated-switching-both-ends {
      type boolean;
      description
        "The C&SC is operating such that switching at both ends of each flow across the FC is coordinated at both ingress and egress ends.";
    }
    leaf-list subordinate-control {
      type leafref {
        path "/core-model:configuration-and-switch-control/core-model:switch-rule";
      }
      description
        "A C&SC that is fully or partially subordinate this C&SC. 
         A peer is considered as partially subordinate in that the peer will respond to requests for action from this C&SC but will also make requests for action to be carried out by this C&SC.
         Where there is a peer relationship each controller in the peering will see the other controller as subordinate.";
    }
    leaf casc-spec {
      type leafref {
        path "/core-model:configuration-and-switch-control/core-model:switch-rule";
      }
      description
        "none";
    }
    leaf-list encapsulated-casc {
      type leafref {
        path "/core-model:configuration-and-switch-control/core-model:switch-rule";
      }
      description
        "Where a C&SC is complex it may be decomposed into subordinate C&SC parts.
         The decomposition is described by the C&SC spec.";
    }
    leaf-list casc-port {
      type leafref {
        path "/core-model:casc-port/core-model:uuid";
      }
      description
        "A reference to ports of a C&SC that can be used where there is significant asymmetry to be represented.
         The C&SC need not have ports.";
    }
    leaf-list coordinated-fc {
      type leafref {
        path "/core-model:forwarding-construct/core-model:uuid";
      }
      description
        "none";
    }
    leaf resilience-control-status {
      type resilience-control;
      description
        "none";
    }
    description
      "Represents the capability to control and coordinate switches, to add/delete/modify FCs and to add/delete/modify LTPs/LPs so as to realize a protection scheme.";
  }

  grouping control-parameters-pac-g {
    leaf reversion-mode {
      type reversion-mode;
      description
        "Indicates whether the protection scheme is revertive or non-revertive.";
    }
    leaf wait-to-revert-time {
      type uint64;
      default "15";
      description
        "If the protection system is revertive, this attribute specifies the time, in minutes, to wait after a fault clears on a higher priority (preferred) resource before switching to the preferred resource.
         If a further fault occurs on the preferred resource in the waitToRevertTime then the reversion attempt is cancelled.
         The WTR timer is overridden by the needs of a higher priority signal. Depending upon which resource is requested this may simply cancel the attempt to revert of may cause immediate reversion.";
    }
    leaf prot-type {
      type protection-type;
      description
        "Indicates the protection scheme that is used for the ProtectionGroup.";
    }
    leaf hold-off-time {
      type uint64;
      description
        "This attribute indicates the time, in milliseconds, between declaration of a switch trigger condition (e.g. signal degrade or signal fail), and the initialization of the protection switching algorithm.";
    }
    leaf network-scheme-specification {
      type leafref {
        path "/core-model:network-scheme-specification/core-model:scheme-name";
      }
      description
        "none";
    }
    uses global-class-g;
    description
      "A list of control parameters to apply to a switch.";
  }

  grouping fc-route-g {
    leaf-list fc {
      type leafref {
        path "/core-model:forwarding-construct/core-model:uuid";
      }
      description
        "The list of FCs describing the route of an FC.
         In most cases the FcRoute has 2 or more FCs however there are some cases where a Route with one FC is valid.";
    }
    leaf selection-priority {
      type uint64;
      description
        "The preference priority of the resource in the resilience scheme for a particular FC. 
         The lower the value the higher the priority.
         A lower value of selection priority is preferred
         If two resources have the same value they are of equal priority.
         There is no preference between equal priorities.
         If a resource with the lowest value selection priority fails, then the next lowest value available (may be the same value) is picked.
         Hence on failure of the current resource the next best available will be selected.
         If there are several equal values, the choice is essentially arbitrary).
         If the scheme is revertive then when a resource of higher priority than the currently selected resource recovers it will be selected.
         This is equivalent to working/protection but allows for all static scheme types with n:m capability. 
         In simple schemes 0 = working and 1 = protecting.
         If selection priority of a Route is increased in value and the Route is currently selecting this Route, then if another Route of a lower selection priority value is available the wait to restore process will come into action as if the other Route had just become available.
         If selection priority of a Route is changed and the FC is not currently selecting this Route but is selecting an item that is now of a higher numeric value than the changed Route, then the wait to restore process will come into action as if the other Route had just become available.";
    }
    leaf route-selection-control {
      type string;
      description
        "Degree of administrative control applied to the route selection.";
    }
    leaf-list link {
      type leafref {
        path "/core-model:link/core-model:uuid";
      }
      description
        "none";
    }
    uses global-class-g;
    description
      "Each instance of an FC Route (FcRoute) class models an individual route of an FC. The route is an alternative view of the internal structure of the FC to FC aggregation (see FcHasLowerLeverFcs association).
       There are cases where a route is the most appropriate representation and cases where the aggregation approach is the most appropriate representation.
       The route of an FC object is represented by a list of FCs at a lower level with the implicit understanding that unmodeled link connections are interleaved between the lower level FCs. 
       Note that depending on the service supported by an FC, the FC can have multiple routes.
       The FcRoute is also applicable where an NE level ForwardingDomain may be decomposed into subordinate ForwardingDomains. Applies to both virtual and real NE cases.";
  }

  grouping fc-switch-g {
    leaf hold-off-time {
      type uint64;
      description
        "Moved to ControlParameter_Pac... This attribute indicates the time, in seconds, between declaration of unacceptable quality of signal on the currently selected FcPort, and the initialization of the protection switching algorithm. ";
    }
    leaf prot-type {
      type protection-type;
      description
        "Indicates the protection scheme that is used for the ProtectionGroup.";
    }
    leaf reversion-mode {
      type reversion-mode;
      description
        "Moved to ControlParameter_Pac... This attribute whether or not the protection scheme is revertive or non-revertive. ";
    }
    leaf-list selected-fc-port {
      type leafref {
        path "/core-model:forwarding-construct/core-model:fc-port/core-model:local-id";
      }
      description
        "Indicates which points are selected by the switch.
         Depending on the switch spec (via FcSpec)
         - more than one FcPort can be selected at any one time (e.g. egress switch, ingress packet switch)
         - zero FcPorts can  be selected. For an ingress switch this indicates that the switch common (egress) is 'high impedance'
         .";
    }
    leaf-list profile-proxy {
      type leafref {
        path "/core-model:profile-proxy/core-model:profile-proxy-mode";
      }
      description
        "Provides a set of predefined values for switch control in place of the direct values available via the FcSwitch or via _configurationAndSwitchControl.";
    }
    leaf configuration-and-switch-control {
      type leafref {
        path "/core-model:configuration-and-switch-control/core-model:switch-rule";
      }
      description
        "A ConfigurationAndSwitchController that is external to the switch (it is coordinating many switches and hence cannot be encapsulated in the FcSwitch.";
    }
    leaf internal-configuration-and-switch-control {
      type leafref {
        path "/core-model:configuration-and-switch-control/core-model:switch-rule";
      }
      description
        "A ConfigurationAndSwitchController encapsulated in the FcSwitch that controls the FcSwitch alone.";
    }
    leaf switch-control {
      type switch-control;
      description
        "Degree of administrative control applied to the switch selection.";
    }
    leaf switch-selects-ports {
      type port-direction;
      description
        "Indicates whether the switch selects from ingress to the FC or to egress of the FC, or both.";
    }
    leaf control-parameters {
      type leafref {
        path "/core-model:control-parameters/core-model:uuid";
      }
      description
        "none";
    }
    leaf wait-to-restore-time {
      type uint64;
      description
        "Moved to ControlParameter_Pac and changed to waitToRevert... If the protection system is revertive, this attribute specifies the amount of time, in seconds, to wait after the preferred FcPort returns to an acceptable state of operation (e.g. a fault has cleared) before restoring traffic to that preferred FcPort.";
    }
    uses local-class-g;
    description
      "The FcSwitch class models the switched forwarding of traffic (traffic flow) between FcPorts and is present where there is protection functionality in the FC. 
       If an FC exposes protection (having two or more FcPorts that provide alternative identical inputs/outputs), the FC will have one or more associated FcSwitch objects to represent the alternative flow choices visible at the edge of the FC.
       The FC switch represents and defines a protection switch structure encapsulated in the FC and essentially 'decorates' FCs that are involved in resilience schemes that use switching in a protection mechanism. 
       Essentially FcSwitch performs one of the functions of the Protection Group in a traditional model. It associates 2 or more FcPorts each playing the role of a Protection Unit. 
       One or more protection, i.e. standby/backup, FcPorts provide protection for one or more working (i.e. regular/main/preferred) FcPorts where either protection or working can feed one or more protected FcPort.
       The switch may be used in revertive or non-revertive (symmetric) mode. When in revertive mode it may define a waitToRestore time.
       It may be used in one of several modes including source switched, destination switched, source and destination switched etc. (covering cases such as 1+1 and 1:1).
       It may be locked out (prevented from switching), force switched or manual switched.
       It will indicate switch state and change of state.
       The switch can be switched away from all sources such that it becomes open and hence two coordinated switches can both feed the same LTP so long as at least one of the two is switched away from all sources (is 'open').
       The ability for a Switch to be 'high impedance' allows bidirectional ForwardingConstructs to be overlaid on the same bidirectional LTP where the appropriate control is enabled to prevent signal conflict.
       This ability allows multiple alternate routes to be present that otherwise would be in conflict.";
  }

  grouping casc-port-g {
    leaf port-role {
      type string;
      description
        "The role of the port of a C&SC. 
         The interpretation of the role is provided by the C&SC spec.
         The C&SC spec will set out the role in the context of C&SC functions.
         The role will indicate how the port relates to the associated entity, e.g. is conveying messages.";
    }
    leaf port-role-properties {
      type leafref {
        path "/core-model:casc-port-role-properties/core-model:uuid";
      }
      description
        "A link to properties associated with the port role as defined by the CascSpec.";
    }
    leaf-list ltp {
      type leafref {
        path "/core-model:logical-termination-point/core-model:uuid";
      }
      description
        "The LTP that conveys the messages related to the port and/or is subject to control action and/or provides indications of state etc.
         For direct association, there may be up to 2 LTPs (to account for directionality differences).
         In the specification representation, there may be a number rules that provide further LTP relationships that are implicit in the instantiated model.";
    }
    leaf encapsulating-casc-port {
      type leafref {
        path "/core-model:casc-port/core-model:uuid";
      }
      description
        "In a case where there is nested C&SC the ports are also nested and this references the superior port.";
    }
    leaf is-related-control-flow-disabled {
      type boolean;
      default "true";
      description
        "If TRUE, then any Control signal flow related to this controller (to, from or drop-and-continue) is prevented from passing through the related LTP carrying the signaling for this controller.
         This can be considered as being realized using an FcSwitch in an FC embedded in the LP at the layer of signaling to disconnect the FcPort bidirectionally.
         This FcSwitch should be represented in the LTP spec.
         Note that the FcSwitch will be at the granularity of the relevant control signal and other flows may be passed uninterrupted.";
    }
    leaf is-controlled-fc-port-disabled {
      type boolean;
      description
        "If TRUE, then the related FcPort on the FC is disabled and hence signal will not flow through that FcPort.
         This is realized using an FcSwitch to disconnect the FcPort bidirectionally.
         Note that as the controller may control many FCs and may switch them all together as one, in an implementation the FcSwitch could be omitted from the FC instance model.
         Any omission should be explained by the FcSpec.
         This is equivalent to a blocked indication on the LTP used in other representations.";
    }
    leaf is-protection-lock-out {
      type boolean;
      description
        "The resource is configured to temporarily not be available for use in the protection scheme(s) it is part of.
         This overrides all other protection control states including forced.
         If the item is locked out, then it cannot be used under any circumstances.
         This causes isRelatedControlFlowDisabled to become TRUE and isControlledFcPortDisabled to become TRUE.";
    }
    uses global-class-g;
    description
      "A port of a C&SC that can be used where there is significant asymmetry to be represented.
       This can represent any combination of:
       - the conveying of messaging to/from the C&SC
       - the conveying of control action
       - the providing of indications of state etc.";
  }

  grouping casc-port-role-properties-g {
    leaf signalling-format {
      type string;
      description
        "none";
    }
    leaf monitoring-detail {
      type string;
      description
        "none";
    }
    leaf control-details {
      type string;
      description
        "none";
    }
    uses global-class-g;
    description
      " Container for properties associated with the port role as defined by the CascSpec.";
  }

  grouping clock-g {
    leaf run-mode {
      type run-mode;
      config false;
      description
        "The run-mode of the frequency system clock, such as free-run, locked, and holdover.";
    }
    leaf-list encompassed-clock {
      type leafref {
        path "/core-model:clock/core-model:local-id";
      }
      description
        "A clock may be emergent from and may effectively encompass several clocks in a resilient solution.";
    }
    leaf-list encapsulated-fc {
      type leafref {
        path "/core-model:forwarding-construct/core-model:uuid";
      }
      description
        "A Clock may encapsulate an FC related to resilience where the clock provides an output that is essentially that of one of several other clocks in the resilience scheme.";
    }
    leaf-list output-ltp {
      type leafref {
        path "/core-model:logical-termination-point/core-model:uuid";
      }
      description
        "A clock may feed one or more LTPs with timing information to propagate across the network (it may feed no LTPs).";
    }
    leaf-list encapsulated-casc {
      type leafref {
        path "/core-model:configuration-and-switch-control/core-model:switch-rule";
      }
      description
        "The clock may encapsulate a complex FC where there is a resilience mechanism active and that FC will need to be controlled. 
         The Casc to control the FC can be encapsulated in the Clock.";
    }
    leaf-list phase-aligned-clock {
      type leafref {
        path "/core-model:clock/core-model:local-id";
      }
      description
        "One or more clocks can be actively phase aligned (this is especially relevant in a hitless resilience scheme).";
    }
    uses local-class-g;
    description
      "Clock function processes the input sync information (frequency and ssm or time stamp and PTP announce messages) and provides the modified sync information to the sync distribution function.
       If none of the inputs meet the quality defined by the controller the clock may enter a hold-over or free run mode. 
       The status of the clock will be reported to the controller.";
  }

  grouping forwarding-domain-g {
    leaf-list layer-protocol-name {
      type layer-protocol-name;
      min-elements 1;
      description
        "One or more protocol layers at which the FD represents the opportunity to enable forwarding between LTP that bound it.";
    }
    leaf-list lower-level-fd {
      type leafref {
        path "/core-model:forwarding-domain/core-model:uuid";
      }
      description
        "The FD class supports a recursive aggregation relationship (HigherLevelFdEncompassesLowerLevelFds) such that the internal construction of an FD can be exposed as multiple lower level FDs and associated Links (partitioning).
         The aggregated FDs and Links form an interconnected topology that provides and describes the capability of the aggregating FD.
         Note that the model actually represents an aggregation of lower level FDs into higher level FDs as views rather than FD partition, and supports multiple views. 
         Aggregation allow reallocation of capacity from lower level FDs to different higher level FDs as if the network is reorganized  (as the association is aggregation not composition).";
    }
    leaf-list fc {
      type leafref {
        path "/core-model:forwarding-construct/core-model:uuid";
      }
      description
        "An FD aggregates one or more FCs. An aggregated FC connects LTPs that bound the FD.";
    }
    leaf-list ltp {
      type leafref {
        path "/core-model:logical-termination-point/core-model:uuid";
      }
      description
        "An instance of FD is associated with zero or more LTP objects. 
         The LTPs that bound the FD provide capacity for forwarding.
         For asymmetric FDs, the association to the LTP is via the FdPort.";
    }
    leaf-list lower-level-link {
      type leafref {
        path "/core-model:link/core-model:uuid";
      }
      description
        "The FD encompasses Links that interconnect lower level FDs and collect Links that are wholly within the bounds of the FD.
         See also _lowerLevelFd.";
    }
    leaf fd-rule-set {
      type leafref {
        path "/core-model:fd-and-link-rule-set/core-model:uuid";
      }
      description
        "The rules related to an FD.";
    }
    leaf layer-protocol-parameter-spec {
      type string;
      description
        "none";
    }
    leaf-list fd-spec {
      type leafref {
        path "/core-model:forwarding-domain/core-model:uuid";
      }
      description
        "none";
    }
    list fd-port {
      key "local-id";
      uses fd-port-g;
      description
        "The association of the FD to LTPs is either made directly for symmetric FDs or via FdPort for asymmetric FDs.";
    }
    leaf-list pc {
      type leafref {
        path "/core-model:processing-construct/core-model:uuid";
      }
      description
        "An FD constrains one or more PCs. A constrained PC connects LTPs on the boundary of the FD";
    }
    uses global-class-g;
    uses forwarding-entity-g;
    description
      "The ForwardingDomain (FD) class models the topological component that represents a forwarding capability that provides the opportunity to enable forwarding (of specific transport characteristic information at one or more protocol layers) between points.
       The FD object provides the context for and constrains the formation, adjustment and removal of FCs and hence offers the potential to enable forwarding.
       The FCs may be formed between LTPs at the boundary of the FD or between physical ports at the boundary of the FD (for media layers).
       A number of FDs (related by Links) may be grouped and abstracted to form an FD where that FD represents the effect of the underlying FDs but where the detailed structure is not apparent.
       This grouping and abstraction is potentially recursive.
       An FD represents an abstraction of some combination of software behavior, electronic behavior and physical structure that provides a forwarding capability. 
       At a lower level of recursion an FD could represent a forwarding capability within a device. 
       A device may encompass two or more disjoint forwarding capabilities and may support more than one layer protocol, hence more than one FD.
       A routing fabric may be logically partitioned to represent connectivity constraints, hence the FD representing the routing fabric may be partitioned into a number of FDs representing the constraints.
       The FD represents a subnetwork [ITU-T G.800], FlowDomain [TMF 612] and a MultiLayerSubNetwork (MLSN) [TMF 612]. 
       As in the TMF concept of MLSN the FD can support more than one layer-protocol.
       Note that the ITU-T G.800 subnetwork is a single layer entity.";
  }

  grouping forwarding-construct-g {
    leaf layer-protocol-name {
      type layer-protocol-name;
      description
        "The layerProtocol at which the FC enables the potential for forwarding.";
    }
    leaf-list lower-level-fc {
      type leafref {
        path "/core-model:forwarding-construct/core-model:uuid";
      }
      description
        "An FC object supports a recursive aggregation relationship such that the internal construction of an FC can be exposed as multiple lower level FC objects (partitioning).
         Aggregation is used as for the FD to allow changes in hierarchy. 
         FC aggregation reflects FD aggregation. 
         The FC represents what would have traditionally been considered as a 'Cross-Connection' in an 'NE'. The 'Cross-Connection' in an 'NE' is not necessarily the lowest level of FC partitioning.
        ";
    }
    leaf-list fc-route {
      type leafref {
        path "/core-model:fc-route/core-model:uuid";
      }
      description
        "An FC object can have zero or more routes, each of which is defined as a list of lower level FC objects describing the flow across the network.";
    }
    list fc-port {
      key "local-id";
      min-elements 2;
      uses fc-port-g;
      description
        "The FcPorts define the boundary of the FC.
         The FC is accessed via the FcPorts.
         Flow within the FC is defined in terms of its FcPorts.";
    }
    leaf-list fc-switch {
      type leafref {
        path "/core-model:fc-switch/core-model:local-id";
      }
      description
        "If an FC exposes protection (having two FcPorts that provide alternative identical inputs/outputs), the FC will have one or more associated FcSwitch objects.
         The arrangement of switches for a particular instance is described by a referenced FcSpec";
    }
    leaf-list configuration-and-switch-control {
      type leafref {
        path "/core-model:configuration-and-switch-control/core-model:switch-rule";
      }
      description
        "Reference to a ConfigurationAndSwitchController that coordinates switches encapsulated in the FC.
         The controller coordinates multiple switches in the same FC.";
    }
    leaf forwarding-direction {
      type forwarding-direction;
      description
        "The directionality of the ForwardingConstruct. 
         Is applicable to simple ForwardingConstructs where all FcPorts are BIDIRECTIONAL (the ForwardingConstruct will be BIDIRECTIONAL) or UNIDIRECTIONAL (the ForwardingConstruct will be UNIDIRECTIONAL). 
         Is not present in more complex cases.
         In the case of media the FcPorts and FC may also be omni-directional.";
    }
    leaf is-protection-lock-out {
      if-feature "_7jInkMOBEeWwZ527PhfFSA";
      type boolean;
      description
        "The resource is configured to temporarily not be available for use in the protection scheme(s) it is part of.
         This overrides all other protection control states including forced.
         If the item is locked out then it cannot be used under any circumstances.
         Note: Only relevant when part of a protection scheme.";
    }
    leaf service-priority {
      type uint64;
      description
        "Relevant where 'service' FCs are competing for server resources.
         Used to determine which signal FC is allocated resource. 
         The priority of the 'service' with respect to other 'services'. 
         Lower numeric value means higher priority. 
         Covers cases such as pre-emptible in a resilience solution. ";
    }
    list fc-spec-reference-class-ref {
      if-feature "_xZ8AIGFxEeerc4Zz6ufSeg";
      key "name";
      min-elements 1;
      uses metaclass-class-g;
      description
        "Reference to the Spec (Class).";
    }
    leaf-list supported-link {
      type leafref {
        path "/core-model:link/core-model:uuid";
      }
      description
        "An FC that spans between LTPs that terminate the LayerProtocol usually supports one or more links in the client layer.";
    }
    uses global-class-g;
    uses forwarding-entity-g;
    description
      "The ForwardingConstruct (FC) class models enabled constrained potential for forwarding between two or more FcPorts at a particular specific layerProtocol .
       Like the LTP, the FC supports any transport protocol including all analogue, circuit and packet forms.
       For digital layer networks it is used to effect forwarding of transport characteristic (layer protocol) information.
       An FC can be in only one ForwardingDomain (FD).
       The FC is a forwarding entity.
       At a low level of the recursion, a FC represents a cross-connection within an NE. It may also represent a fragment of a cross-connection under certain circumstances.
       The FC object can be used to represent many different structures including point-to-point (P2P), point-to-multipoint (P2MP), rooted-multipoint (RMP) and multipoint-to-multipoint (MP2MP) bridge and selector structures for linear, ring or mesh protection schemes.
       When applied to media, the FC represents the ability for a flow/wave (potentially containing information), to be propagated between FcPorts. 
       The existence of a FC instance is independent of the presence (or absence) of a flow/wave (and any information encoded within it).  
       A flow/wave cannot propagate in the absence of a FC instance.";
  }

  grouping link-g {
    leaf-list layer-protocol-name {
      type layer-protocol-name;
      min-elements 1;
      description
        "The Link can support multiple transport layer protocols via the associated LTP object. 
         For implementation optimization, where appropriate, multiple layer-specific Links can be merged and represented as a single Link instance as the Link can represent a list of layer protocols.
         A Link may support different layer protocols at each Port when it is a transitional Link.";
    }
    leaf-list fd {
      type leafref {
        path "/core-model:forwarding-domain/core-model:uuid";
      }
      min-elements 2;
      description
        "The Link associates with two or more FDs. 
         This association provides a direct summarization of the association via LinkPort and LTP.";
    }
    list link-port {
      key "local-id";
      min-elements 2;
      uses link-port-g;
      description
        "The association of the Link to LTPs is made via LinkPort (essentially the ports of the Link).";
    }
    leaf-list lower-level-link {
      type leafref {
        path "/core-model:link/core-model:uuid";
      }
      description
        "A Link may be formed from subordinate links (similar FD formations from subordinate FDs). This association is intended to cover concepts such as serial compound links. ";
    }
    leaf link-direction {
      type forwarding-direction;
      description
        "The directionality of the Link. 
         Is applicable to simple Links where all LinkPorts are BIDIRECTIONAL (the Link will be BIDIRECTIONAL) or UNIDIRECTIONAL (the Link will be UNIDIRECTIONAL). 
         Is not present in more complex cases.";
    }
    leaf fd-rule-set {
      type leafref {
        path "/core-model:fd-and-link-rule-set/core-model:uuid";
      }
      description
        "The rules related to a Link.";
    }
    leaf is-protection-lock-out {
      if-feature "_52M5wMODEeWwZ527PhfFSA";
      type boolean;
      description
        "The resource is configured to temporarily not be available for use in the protection scheme(s) it is part of.
         This overrides all other protection control states including forced.
         If the item is locked out, then it cannot be used under any circumstances.
         Note: Only relevant when part of a protection scheme.";
    }
    leaf-list fc {
      type leafref {
        path "/core-model:forwarding-construct/core-model:uuid";
      }
      description
        "A Link contains one or more FCs. A contained FC connects LTPs that bound the Link. 
         This FC represents the traditional link connection. It is often not supported in implementations as it can be inferred from FCs in the corresponding FDs.";
    }
    leaf-list lower-level-fd {
      type leafref {
        path "/core-model:forwarding-domain/core-model:uuid";
      }
      description
        "FD(s) that form part of a serial compound Link.";
    }
    leaf link-spec {
      type leafref {
        path "/core-model:link/core-model:uuid";
      }
      description
        "none";
    }
    list link-spec-reference-class-ref {
      if-feature "_wL2cYGFxEeerc4Zz6ufSeg";
      key "name";
      min-elements 1;
      uses metaclass-class-g;
      description
        "none";
    }
    uses global-class-g;
    uses forwarding-entity-g;
    description
      "The Link class models effective adjacency between two or more ForwardingDomains (FD). 
       For digital layer networks, in its basic form (i.e., point-to-point Link) it associates a set of LTP clients on one FD with an equivalent set of LTP clients on another FD. 
       Like the FC, the Link has ports (LinkPort) which take roles relevant to the constraints on flows offered by the Link (e.g., Root role or leaf role for a Link that has a constrained Tree configuration).";
  }

  grouping fc-port-g {
    leaf-list ltp {
      type leafref {
        path "/core-model:logical-termination-point/core-model:uuid";
      }
      max-elements "2";
      description
        "The FcPort may be associated with more than one LTP when the FcPort is bidirectional and the LTPs are unidirectional.
         Multiple LTP
         - Bidirectional FcPort to two Uni-directional LTPs
         Zero LTP
         - BreakBeforeMake transition
         - Planned LTP not yet in place
         - Off-network LTP referenced through other mechanism.";
    }
    leaf role {
      type port-role;
      description
        "Each FcPort of the FC has an assigned role (e.g., working, protection, protected, symmetric, hub, spoke, leaf, root) in the context of the FC with respect to the FC function. 
         The role is fixed by the referenced FcSpec.";
    }
    leaf fc-port-direction {
      type port-direction;
      description
        "The orientation of the defined flow at the FcPort.";
    }
    leaf is-protection-lock-out {
      if-feature "_RrjlUMOEEeWwZ527PhfFSA";
      type boolean;
      description
        "The resource is configured to temporarily not be available for use in the protection scheme(s) it is part of.
         This overrides all other protection control states including forced.
         If the item is locked out, then it cannot be used under any circumstances.
         Note: Only relevant when part of a protection scheme.";
    }
    leaf selection-priority {
      type uint64;
      description
        "The preference priority of the resource in the protection scheme for a particular FC. 
         The lower the value the higher the priority.
         A lower value of selection priority is preferred
         If two resources have the same value they are of equal priority.
         There is no preference between equal priorities.
         If a resource with the lowest value selection priority fails,, then the next lowest value available (may be the same value) is picked.
         Hence on failure of the current resource the next best available will be selected.
         If there are several equal values, the choice is essentially arbitrary.
         If the scheme is revertive then when a resource of higher priority than the currently selected resource recovers it will be selected.
         This is equivalent to working/protection but allows for all static scheme types with n:m capability. 
         In simple schemes 0 = working and 1 = protecting.
         If selection priority of an FcPort is increased in value and the FC is currently selecting this FcPort then if another FcPort of a lower selection priority value is available, the wait to restore process will come into action as if the other FcPort had just become available.
         If selection priority of a FcPort is changed and the FC is not currently selecting this FcPort but is selecting an item that is now of a higher numeric value than the changed FcPort then the wait to restore process will come into action as if the other FcPort had just become available.";
    }
    leaf is-internal-port {
      type boolean;
      config false;
      description
        "The FcPort is not exposed and cannot have associated LTPs.
         This form of FcPort is used to enable chaining of FcSwitches or FcRoutes in complex network protection scenarios.";
    }
    leaf-list fc-route-feeds-fc-port-egress {
      type leafref {
        path "/core-model:fc-route/core-model:uuid";
      }
      description
        "Identifies which route(s) currently actively forward to the FcPort to exit the FC to an LTP (or for an internal FcPort to propagate to the next internal switch/route).";
    }
    leaf-list fc-port {
      type leafref {
        path "/core-model:forwarding-construct/core-model:fc-port/core-model:local-id";
      }
      max-elements "2";
      description
        "An FcPort may have a direct association to another FcPort where there is a transition from one domain to another but where there has been no termination.";
    }
    leaf-list port-of-internal-fc {
      type leafref {
        path "/core-model:forwarding-construct/core-model:fc-port/core-model:local-id";
      }
      description
        "none";
    }
    leaf pin {
      type leafref {
        path "/core-model:pin/core-model:position";
      }
      description
        "For media FCs, the name of the pin that terminates the media.";
    }
    uses local-class-g;
    description
      "The association of the FC to LTPs is always made via FcPorts.
       In the case of media the association between FCs is made via their FcPorts and the association of an FC to the physical Pin is made via the FcPort.
       The FcPort class models the access to the FC function. 
       The traffic forwarding between the associated FcPorts of the FC depends upon the type of FC and may be associated with FcSwitch object instances.  
       In cases where there is resilience, the FcPort may convey the resilience role of the access to the FC. 
       It can represent a protected (resilient/reliable) point or a protecting (unreliable working or protection) point.
       The FcPort replaces the Protection Unit of a traditional protection model. 
       The ForwardingConstruct can be considered as a component and the FcPort as a Port on that component.";
  }

  grouping layer-protocol-g {
    leaf layer-protocol-name {
      type layer-protocol-name;
      description
        "Indicate the specific layer-protocol described by the LayerProtocol entity.";
    }
    leaf configured-client-capacity {
      type to-be-defined;
      description
        "Provides a summarized view of the client capacity that is configurable for use.
         Note the client LTP association should provide all necessary detail hence this attribute is questionable.";
    }
    leaf lp-direction {
      type termination-direction;
      description
        "The overall directionality of the LP. 
         - A BIDIRECTIONAL LP will have some SINK and/or SOURCE flows.
         - A SINK LP can only contain elements with SINK flows or CONTRA_DIRECTION_SOURCE flows
         - A SOURCE LP can only contain SOURCE flows or CONTRA_DIRECTION_SINK flows";
    }
    leaf termination-state {
      type termination-state;
      description
        "Indicates whether the layer is terminated and if so how.";
    }
    leaf-list configuration-and-switch-control {
      type leafref {
        path "/core-model:configuration-and-switch-control/core-model:switch-rule";
      }
      description
        "A switch controller external to the LayerProtocol.
         The controller will coordinate one or more switches in one or more FCs related to the LayerProtocol";
    }
    leaf is-protection-lock-out {
      type boolean;
      description
        "The resource is configured to temporarily not be available for use in the protection scheme(s) it is part of.
         This overrides all other protection control states including forced.
         If the item is locked out, then it cannot be used under any circumstances.
         Note: Only relevant when part of a protection scheme.";
    }
    leaf fc-blocks-signal-to-lp {
      type string;
      description
        "none";
    }
    list lp-spec-reference-class-ref {
      if-feature "_n0WVAWFoEeeiJ9-h1KDHig";
      key "name";
      uses metaclass-class-g;
      description
        "none";
    }
    uses local-class-g;
    description
      "The projection of an LTP into each transport layer is represented by a LayerProtocol (LP) instance. A LayerProtocol instance can be used for controlling termination and monitoring functionality. 
       It can also be used for controlling the adaptation (i.e. encapsulation and/or multiplexing of client signal), tandem connection monitoring, traffic conditioning and/or shaping functionality at an intermediate point along a connection. 
       Where the client – server relationship is fixed 1:1 and immutable, the layers can be encapsulated in a single LTP instance. Where there is a n:1 relationship between client and server, the layers must be split over two separate instances of LTP. ";
  }

  grouping logical-termination-point-g {
    leaf-list server-ltp {
      type leafref {
        path "/core-model:logical-termination-point/core-model:uuid";
      }
      description
        "References contained LTPs representing servers of this LTP in an inverse multiplexing configuration (e.g. VCAT).";
    }
    leaf-list client-ltp {
      type leafref {
        path "/core-model:logical-termination-point/core-model:uuid";
      }
      description
        "References contained LTPs representing client traffic of this LTP for normal cases of multiplexing.";
    }
    leaf-list lp {
      type leafref {
        path "/core-model:layer-protocol/core-model:local-id";
      }
      min-elements 1;
      description
        "Ordered list of LayerProtocols that this LTP is comprised of where the first entry in the list is the lowest server layer (e.g. physical).";
    }
    leaf connected-ltp {
      type leafref {
        path "/core-model:logical-termination-point/core-model:uuid";
      }
      description
        "Applicable in a simple context where two LTPs are associated via a non-adjustable enabled forwarding.
         Reduces clutter removing the need for two additional LTPs and an FC with a pair of FcPorts.";
    }
    leaf peer-ltp {
      type leafref {
        path "/core-model:logical-termination-point/core-model:uuid";
      }
      description
        "References contained LTPs representing the reversal of orientation of flow where two LTPs are associated via a non-adjustable enabled forwarding and where the referenced LTP is fully dependent on this LTP.";
    }
    leaf-list physical-port-reference {
      type string;
      description
        "One or more text labels for the unmodeled physical port associated with the LTP.
         In many cases there is no associated physical port.";
    }
    leaf-list ltp-in-other-view {
      type leafref {
        path "/core-model:logical-termination-point/core-model:uuid";
      }
      description
        "References one or more LTPs in other views that represent this LTP. 
         The referencing LTP is the provider of capability.";
    }
    leaf ltp-direction {
      type termination-direction;
      description
        "The overall directionality of the LTP. 
         - A BIDIRECTIONAL LTP must have at least some LPs that are BIDIRECTIONAL but may also have some SINK and/or SOURCE LPs.
         - A SINK LTP can only contain SINK LPs
         - A SOURCE LTP can only contain SOURCE LPs";
    }
    leaf access-port {
      type string;
      description
        "Provides a reference to the place where the signal is accessed. 
         It may represent a physical place (some part of one or more connectors) or a virtual equivalent where there is no further protocol layering (visible).";
    }
    leaf transfer-capacity-pac {
      type leafref {
        path "/core-model:forwarding-construct/core-model:transfer-capacity-pac/core-model:capacity-interaction-algorithm";
      }
      description
        "The LTP has as an inherent capacity derived from underlying capability.
         The capacity of a particular LTP may be dependent upon other uses of resource in the device and hence it may vary over time.
         The capacity of a Link is dependent upon the capacity of the LTPs at its ends.
         An LTP may be an abstraction and virtualization of a subset of the underlying capability offered in a view or may be directly reflecting the underlying realization.";
    }
    list ltp-spec-reference-class-ref {
      if-feature "_TNTy0GFYEeeiJ9-h1KDHig";
      key "name";
      min-elements 1;
      uses metaclass-class-g;
      description
        "Provides a reference to a specification which is in the form of a class definition.
         An instance of LTP will reference a class (by a universally unique id) that provides definition that extends the LTP including attributes and structure that are present in the LTP instance but that are not defined in the native LTP class.
        ";
    }
    leaf-list fd-rule-group {
      type leafref {
        path "/core-model:forwarding-domain/core-model:uuid";
      }
      description
        "An LTP can reference FD rules that the FD that aggregates it also references so that the rules can then apply to the LTP.";
    }
    leaf-list embedded-clock {
      type leafref {
        path "/core-model:clock/core-model:local-id";
      }
      description
        "none";
    }
    uses global-class-g;
    description
      "The LogicalTerminationPoint (LTP) class encapsulates the termination and adaptation functions of one or more transport layers represented by instances of LayerProtocol.
       The encapsulated transport layers have a simple fixed 1:1 client-server relationship defined by association end ordering.
       The structure of LTP supports all transport protocols including circuit and packet forms.";
  }

  grouping link-port-g {
    leaf-list ltp {
      type leafref {
        path "/core-model:logical-termination-point/core-model:uuid";
      }
      description
        "The LinkPort may be associated with more than one LTP when the LinkPort is bidirectional and the LTPs are unidirectional.
         Multiple LTP
         - Bidirectional LinkPort to two Uni-directional LTPs
         Zero LTP
         - BreakBeforeMake transition
         - Planned LTP not yet in place
         - Off-network LTP referenced through other mechanism.";
    }
    leaf role {
      type port-role;
      description
        "Each LinkPort of the Link has a role (e.g., symmetric, hub, spoke, leaf, root) in the context of the Link with respect to the Link capability. ";
    }
    leaf off-network-address {
      type string;
      description
        "A freeform opportunity to express a reference for a Port of the Link that is not visible and hence is outside the scope of the control domain (off-network).
         This attribute is expected to convey a foreign identifier/name/address or a shared reference for some mid-span point at the boundary between two administrative domains.
         This is a reference shared between the parties either side of the network boundary. 
         The assumption is that the provider knows the mapping between network port and offNetworkAddress and the client knows the mapping between the client port and the offNetworkAddress and that the offNetworkAddress references some common point or pool of points. 
         It may represent some physical location where the hand-off takes place. This attribute is used when an LTP cannot be referenced.
         A Link with an Off-network end cannot be encompassed by an FD.";
    }
    leaf link-port-direction {
      type port-direction;
      description
        "The orientation of the defined flow at the LinkPort.";
    }
    leaf-list fc-port {
      type leafref {
        path "/core-model:forwarding-construct/core-model:fc-port/core-model:local-id";
      }
      description
        "Where a Link supports FCs each LinkPort of that Link supports the corresponding FcPorts.";
    }
    uses local-class-g;
    description
      "The association of the Link to LTPs is made via LinkPort.
       The LinkPort class models the access to the Link function. 
       The traffic forwarding between the associated LinkPorts of the Link depends upon the type of Link.  
       In cases where there is resilience, the LinkPort may convey the resilience role of the access to the Link. 
       The Link can be considered as a component and the LinkPort as a Port on that component.";
  }

  grouping fd-port-g {
    leaf-list ltp {
      type leafref {
        path "/core-model:logical-termination-point/core-model:uuid";
      }
      max-elements "2";
      description
        "An instance of FD is associated with zero or more LTP objects. 
         The LTPs that bound the FD provide capacity for forwarding.
         For asymmetric FDs, the association to the LTP is via the FdPort.";
    }
    leaf role {
      type port-role;
      description
        "Each FdPort of the FD has a role (e.g., symmetric, hub, spoke, leaf, root) in the context of the FD with respect to the FD capability. ";
    }
    leaf fd-port-direction {
      type port-direction;
      description
        "The orientation of the defined flow at the FdPort.";
    }
    leaf-list fc-port {
      type leafref {
        path "/core-model:forwarding-construct/core-model:fc-port/core-model:local-id";
      }
      description
        "Where an FD is asymmetric and hence has FdPorts and where that FD and supports FCs, appropriate FdPorts of that FD support the corresponding FcPorts.";
    }
    leaf pin {
      type leafref {
        path "/core-model:pin/core-model:position";
      }
      description
        "For media, a pin on the boundary of the FD.";
    }
    leaf-list fd-port {
      type leafref {
        path "/core-model:fd-port/core-model:local-id";
      }
      max-elements "2";
      description
        "An FdPort may have a direct association to another FdPort where there is a transition from one domain to another but where there has been no termination.";
    }
    uses local-class-g;
    description
      "The association of the FD to LTPs may be direct for symmetric FDs and may be via FdPort for asymmetric FDs.
       The FdPort class models the role of the access to the FD function. 
       The capability to set up FCs between the associated FdPorts of the FD depends upon the type of FD. It is asymmetry in this capability that brings the need for FdPort.  
       The FD can be considered as a component and the FdPort as a Port on that component.";
  }

  feature _7jInkMOBEeWwZ527PhfFSA {
    description
      "In protection context if server of protection where entire server is to be excluded from use for protection.";
  }

  feature _xZ8AIGFxEeerc4Zz6ufSeg {
    description
      "specTargetClass=ForwardingConstruct";
  }

  feature _52M5wMODEeWwZ527PhfFSA {
    description
      "In protection context if server of protection where entire server is to be excluded from use for protection.";
  }

  feature _wL2cYGFxEeerc4Zz6ufSeg {
    description
      "specTargetClass=Link";
  }

  feature _RrjlUMOEEeWwZ527PhfFSA {
    description
      "In protection context where the FcPort is to be excluded from use for protection.";
  }

  feature _n0WVAWFoEeeiJ9-h1KDHig {
    description
      "specTargetClass: LayerProtocol";
  }

  feature _TNTy0GFYEeeiJ9-h1KDHig {
    description
      "specTargetClass: LogicalTerminationPoint";
  }

  typedef date-and-time {
    type string;
    description
      "This primitive type defines the date and time according to the following structure:
       'yyyyMMddhhmmss.s[Z|{+|-}HHMm]' where:
       yyyy    '0000'..'9999'    year
       MM        '01'..'12'            month
       dd        '01'..'31'            day
       hh        '00'..'23'            hour
       mm        '00'..'59'            minute
       ss        '00'..'59'            second
       s        '.0'..'.9'            tenth of second (set to '.0' if EMS or NE cannot support this granularity)
       Z        'Z'                    indicates UTC (rather than local time)
       {+|-}    '+' or '-'            delta from UTC
       HH        '00'..'23'            time zone difference in hours
       Mm        '00'..'59'            time zone difference in minutes.";
  }

  typedef bit-string {
    type string;
    description
      "This primitive type defines a bit oriented string.
       The size of the BitString will be defined in the valueRange property of the attribute; according to ASN.1 (X.680).
       The semantic of each bit position will be defined in the Documentation field of the attribute.";
  }

  typedef printable-string {
    type string;
    description
      "A string that only includes printable characters.";
  }

  typedef to-be-defined {
    type string;
    description
      "This type is used when the actual type of the attribute is expected to be complex but where the type has not yet been developed. 
       This type should only be used for attributes that are experimental.";
  }

  grouping name-g {
    list name {
      key "value-name";
      min-elements 1;
      uses name-and-value-g;
      description
        "List of names.";
    }
    description
      "Name: A property of an entity with a value that is unique in some namespace but may change during the life of the entity. A name carries no semantics with respect to the purpose of the entity.";
  }

  grouping global-class-g {
    list local-id {
      key "value-name";
      uses name-and-value-g;
      description
        "An identifier that is unique in the context of some scope that is less than the global scope.
         (This should be considered in the context of Identifier: A property of an entity/role with a value that is unique within an identifier space, where the identifier space is itself unique, and immutable. The identifier therefore represents the identity of the entity/role. An identifier carries no semantics with respect to the purpose of the entity.)";
    }
    leaf uuid {
      type universal-id;
      description
        "UUID: An identifier that is universally unique
         (This should be considered in the context of Identifier: A property of an entity/role with a value that is unique within an identifier space, where the identifier space is itself globally unique, and immutable. An identifier carries no semantics with respect to the purpose or state of the entity)
         The uuid should be treated as opaque by the user.";
    }
    uses name-g;
    uses label-g;
    uses extension-g;
    uses state-pac-g;
    description
      "Represents a type of thing (an Entity) that has instances which can exist in their own right (independently of any others).
       Entity: Has identity, defined boundary, properties, functionality and lifecycle in a global context.
       (This should be considered in the context of a Class: (usage) The representation of a thing that may be an entity or an inseparable Entity Feature).";
  }

  grouping local-class-g {
    leaf local-id {
      type string;
      description
        "An identifier that is unique in the context of some scope that is less than the global scope.
         (This should be considered in the context of Identifier: A property of an entity/role with a value that is unique within an identifier space, where the identifier space is itself unique, and immutable. The identifier therefore represents the identity of the entity/role. An identifier carries no semantics with respect to the purpose of the entity.)";
    }
    uses name-g;
    uses label-g;
    uses extension-g;
    uses state-pac-g;
    description
      "A LocalClass represents a Feature of an Entity. It is inseparable from a GlobalClass but is a distinct feature of that GlobalClass such that the instances of LocalClass are able to have associations to other instances.
       Feature of an Entity: An inseparable, externally distinguishable part of an entity.
       The mandatory LocalId of the LocalClass instance is unique in the context of the GlobalClass from which it is inseparable.
       (This should be considered in the context of a Class: (usage) The representation of a thing that may be an entity or an inseparable feature of an entity.)
      ";
  }

  grouping label-g {
    list label {
      key "value-name";
      uses name-and-value-g;
      description
        "List of labels.";
    }
    description
      "A property of an entity with a value that is not expected to be unique and is allowed to change. A label carries no semantics with respect to the purpose of the entity and has no effect on the entity behavior or state.";
  }

  grouping extension-g {
    list extension {
      key "value-name";
      uses name-and-value-g;
      description
        "List of simple name-value extensions.";
    }
    description
      "Extension provides an opportunity to define properties not declared in the class that extend the class enabling a realization with simple ad-hoc extension of standard classes to be conformant.";
  }

  grouping universal-id-authority-g {
    leaf uuid {
      type universal-id;
      description
        "The UUID for the UUID authority.";
    }
    description
      "Represents the authority that controls the allocation of UUIDs.";
  }

  grouping name-and-value-authority-g {
    leaf uuid {
      type universal-id;
      description
        "The UUID for the NameAndValueAuthority.";
    }
    description
      "Represents the authority that controls the legal values for the names and values of a name/value attribute.";
  }

  grouping conditional-package-g {
    uses extension-g;
    uses label-g;
    description
      "The base class for conditional packages.";
  }

  grouping name-and-value-g {
    leaf value-name {
      type string;
      description
        "The name of the value. The value need not have a name.";
    }
    leaf value {
      type string;
      description
        "The value.";
    }
    leaf name-and-value-authority {
      type leafref {
        path "/core-model:name-and-value-authority/core-model:uuid";
      }
      description
        "The authority that defines the named value.";
    }
    description
      "A scoped name-value pair.";
  }

  typedef universal-id {
    type string;
    description
      "The universal ID value where the mechanism for generation is defined by some authority not directly referenced in the structure.
       An example structure is [IETF RFC4122].";
  }

  grouping address-g {
    leaf address-name {
      type string;
      description
        "The name of the address (to allow the specific hierarchy to be distinguished from others for the same entity).";
    }
    list address-element {
      key "uuid";
      uses address-element-g;
      description
        "The elements of the address that form the recursive scope narrowing.";
    }
    description
      "A description of location via a hierarchy of narrowing contexts.";
  }

  grouping local-id-and-class-g {
    leaf class-of-instance {
      type string;
      description
        "The class to which the name refers.";
    }
    container local-id {
      uses name-and-value-g;
      description
        "The localId of the entity.";
    }
    description
      "The localId and the class of entity that it identifies.";
  }

  grouping name-and-class-g {
    leaf class-of-instance {
      type string;
      description
        "The class to which the name refers.";
    }
    container name {
      uses name-and-value-g;
      description
        "If the element is a name.";
    }
    description
      "The name and the class of entity that it names.";
  }

  grouping address-element-g {
    leaf address-element-name {
      type string;
      description
        "The name of the address element (e.g. 'shelf' as an element of a shelf/slot/port addressing scheme).
         The remainder of the structure has the reference for the shelf.
        ";
    }
    container local-id {
      uses local-id-and-class-g;
      description
        "If the element is a localId (where the element above in the hierarchy must be the context in which the specific localId is relevant).";
    }
    leaf uuid {
      type universal-id;
      description
        "If the element is a uuid (where this element could be the top of a hierarchy but may also be at some level in the hierarchy where address navigation is considered necessary to assist in location of the UUID).";
    }
    container name {
      uses name-and-class-g;
      description
        "If the element is a name.";
    }
    leaf arbitrary-element {
      type string;
      description
        "Where the element is from some external model that is not formally represented in this model.";
    }
    description
      "One element of a hierarchy of elements.
       Note that the element must have one and only one value chosen from a list of potential value types.";
  }

  grouping state-pac-g {
    leaf operational-state {
      type operational-state;
      config false;
      description
        "The operational state is used to indicate whether or not the resource is installed and working.";
    }
    leaf administrative-control {
      type administrative-control;
      description
        "The administrativeControl state provides control of the availability of specific resources without modification to the provisioning of those resources.
         The value is the current control target. The actual administrativeState may or may not be at target.";
    }
    leaf administrative-state {
      type administrative-state;
      config false;
      description
        "Shows whether or not the client has permission to use or has a prohibition against using the resource.
         The administrative state expresses usage permissions for specific resources without modification to the provisioning of those resources.";
    }
    leaf lifecycle-state {
      type lifecycle-state;
      description
        "Used to track the planned deployment, allocation to clients and withdrawal of resources.";
    }
    description
      "Provides general state attributes.";
  }

  typedef operational-state {
    type identityref {
      base operational-state;
    }
    description
      "The operational state is used to indicate whether or not the resource is installed and working. ";
  }

  typedef administrative-state {
    type identityref {
      base administrative-state;
    }
    description
      "The administrative state is used to show whether use of a resource is allowed or prohibited.
       The administrative state can be observed and directly controlled by a certain operational roles. 
       Typically, only a user (in the provider context) with administrative privileges is allowed to write the administrative state, any other users are restricted to read only.";
  }

  typedef administrative-control {
    type identityref {
      base administrative-control;
    }
    description
      "Reflects the current control action when the entity is not in the desired state.";
  }

  typedef lifecycle-state {
    type identityref {
      base lifecycle-state;
    }
    description
      "This state is used to track the planned deployment, allocation to clients and withdrawal of resources.";
  }

  grouping network-scheme-specification-g {
    leaf scheme-name {
      type string;
      description
        "none";
    }
    leaf external-definition-of-scheme {
      type string;
      description
        "none";
    }
    description
      "none";
  }

  grouping profile-proxy-g {
    leaf profile-proxy-mode {
      type uint64;
      description
        "A parameter profile may be used in a number of different ways:
         - Forces the values on the target with no opportunity to see or override the values in the target
         - Sets the values on the target that can be seen on the target
         - Sets the values on the target and supports override on the target so the target can be set away from the value in the profile
         - etc.";
    }
    leaf control-parameters {
      type leafref {
        path "/core-model:control-parameters/core-model:uuid";
      }
      description
        "The control parameters that can be set int the profile and applied to the target.
         Not all parameters need be selected and applied.";
    }
    description
      "A lightweight sketch placeholder for the profile model.";
  }

  grouping lifecycle-scoping-class-g {
    leaf-list composed-dependent {
      type leafref {
        path "/core-model:lifecycle-scoping-class/core-model:uuid";
      }
      description
        "none";
    }
    uses global-class-g;
    description
      "none";
  }

  grouping dependent-class-g {
    leaf lifecycle-scoping-class {
      type leafref {
        path "/core-model:lifecycle-scoping-class/core-model:uuid";
      }
      description
        "none";
    }
    leaf related-lifecycle-scoping-class {
      type leafref {
        path "/core-model:lifecycle-scoping-class/core-model:uuid";
      }
      description
        "none";
    }
    description
      "none";
  }

  typedef action-verbs {
    type identityref {
      base action-verbs;
    }
    description
      "none";
  }

  typedef test-type {
    type string;
    description
      "none";
  }

  typedef activity-directive {
    type identityref {
      base activity-directive;
    }
    description
      "none";
  }

  typedef action-effort {
    type identityref {
      base action-effort;
    }
    description
      "none";
  }

  typedef pause-resume-rule {
    type identityref {
      base pause-resume-rule;
    }
    description
      "none";
  }

  grouping desired-outcome-constraints-g {
    leaf-list outcome-element {
      type leafref {
        path "/core-model:outcome-element-constraints/core-model:uuid";
      }
      min-elements 1;
      description
        "none";
    }
    leaf activity-directive {
      type activity-directive;
      description
        "none";
    }
    leaf has-delete-confirmation {
      type boolean;
      default "true";
      description
        "none";
    }
    leaf number-of-instances-of-each-outcome-element {
      type uint64;
      default "1";
      description
        "none";
    }
    uses global-class-g;
    description
      "none";
  }

  grouping element-constraints-g {
    leaf specific-class-structure {
      type leafref {
        path "/core-model:specific-class-structure/core-model:class-type-name";
      }
      description
        "none";
    }
    leaf specific-pattern {
      type string;
      description
        "none";
    }
    uses global-class-g;
    description
      "none";
  }

  grouping necessary-initial-condition-constraints-g {
    leaf is-not {
      type boolean;
      description
        "none";
    }
    uses global-class-g;
    description
      "none";
  }

  grouping operation-details-g {
    leaf action-verb {
      type action-verbs;
      description
        "none";
    }
    leaf-list necessary-initial-condition-constraints {
      type leafref {
        path "/core-model:necessary-initial-condition-constraints/core-model:uuid";
      }
      description
        "none";
    }
    leaf-list desired-outcome-constraints {
      type leafref {
        path "/core-model:desired-outcome-constraints/core-model:uuid";
      }
      min-elements 1;
      description
        "none";
    }
    uses global-class-g;
    description
      "none";
  }

  grouping operation-envelope-g {
    leaf-list operation-set {
      type leafref {
        path "/core-model:operation-set/core-model:uuid";
      }
      min-elements 1;
      description
        "none";
    }
    leaf general-directives {
      type string;
      description
        "none";
    }
    leaf operation-identifiers {
      type string;
      description
        "none";
    }
    description
      "none";
  }

  grouping operation-set-g {
    leaf-list operation-set-that-must-have-started {
      type leafref {
        path "/core-model:operation-set/core-model:uuid";
      }
      description
        "none";
    }
    leaf-list operation-set-that-must-end {
      type leafref {
        path "/core-model:operation-set/core-model:uuid";
      }
      description
        "none";
    }
    leaf abort-after-duration-with-action-rule {
      type to-be-defined;
      description
        "none";
    }
    leaf effort-and-action {
      type action-effort;
      description
        "none";
    }
    leaf pause-resume-rule {
      type pause-resume-rule;
      description
        "none";
    }
    leaf-list operation-set {
      type leafref {
        path "/core-model:operation-set/core-model:uuid";
      }
      description
        "none";
    }
    leaf is-short-lived {
      type boolean;
      default "true";
      description
        "none";
    }
    leaf-list operation-details {
      type leafref {
        path "/core-model:operation-details/core-model:uuid";
      }
      min-elements 1;
      description
        "none";
    }
    uses global-class-g;
    description
      "none";
  }

  grouping outcome-element-constraints-g {
    uses element-constraints-g;
    description
      "none";
  }

  grouping specific-class-structure-g {
    leaf class-type-name {
      type string;
      description
        "none";
    }
    description
      "none";
  }

  grouping field-replaceable-g {
    leaf-list equipment-non-fru {
      type leafref {
        path "/core-model:equipment/core-model:uuid";
      }
      description
        "none";
    }
    leaf-list holder {
      type leafref {
        path "/core-model:holder/core-model:local-id";
      }
      description
        "none";
    }
    leaf holder-address {
      type leafref {
        path "/core-model:holder/core-model:local-id";
      }
      description
        "none";
    }
    uses equipment-g;
    description
      "A rule class (an abstract specialization of Equipment) that represents an equipment that can be replaced in the field. 
       May plug in to a holder in another equipment (if not stand-alone). 
       Realization could use an FRU Boolean on Equipment.";
  }

  grouping non-field-replaceable-g {
    uses equipment-g;
    description
      "A rule class (an abstract specialization of Equipment) that represents an equipment that cannot be replaced in the field.
       Is simply a subordinate part of an FRU (or another NFRU – where there must be an FRU at the top of the hierarchy). 
       Does not have any exposed holders (any associated holders are assumed to belong to the containing FRU).
       Does not have any connectors (any associated connectors are assumed to belong to the containing FRU).
      ";
  }

  grouping conector-in-holder-g {
    leaf connector-on-equipment-for-holder {
      type leafref {
        path "/core-model:holder/core-model:local-id";
      }
      description
        "none";
    }
    uses connector-g;
    description
      "A rule class (an abstract specialization of Connector) that represents a connector that are only accessible to an equipment inserted in the holder.";
  }

  grouping connector-cable-end-g {
    leaf connector-on-equipment-for-cable {
      type leafref {
        path "/core-model:connector/core-model:local-id";
      }
      description
        "none";
    }
    uses connector-g;
    description
      "A rule class (an abstract specialization of Connector) that represents a connector on the end of a cable.";
  }

  grouping connector-on-equipment-for-cable-g {
    leaf connector-cable-end {
      type leafref {
        path "/core-model:connector/core-model:local-id";
      }
      description
        "none";
    }
    uses connector-g;
    description
      "A rule class (an abstract specialization of Connector) that represents a connector exposed on an equipment such that a cable may be plugged in.";
  }

  grouping connector-on-equipment-for-holder-g {
    leaf conector-in-holder {
      type leafref {
        path "/core-model:holder/core-model:local-id";
      }
      description
        "none";
    }
    uses connector-g;
    description
      "A rule class (an abstract specialization of Connector) that represents a connector on an equipment that is intended to mate with a connector in a holder.";
  }

  grouping function-enablers-g {
    leaf power-state {
      type to-be-defined;
      description
        "none";
    }
    uses global-class-g;
    description
      "Represents the dynamic aspects of the properties that relate to the motive force that directly enable functionality to emerge from the equipment.";
  }

  grouping mechanical-functions-g {
    leaf rotation-speed {
      type to-be-defined;
      description
        "none";
    }
    uses global-class-g;
    description
      "Represents the dynamic aspects of the mechanical functions of the equipment.";
  }

  grouping physical-properties-g {
    leaf temperature {
      type to-be-defined;
      description
        "none";
    }
    uses global-class-g;
    description
      "Represents the dynamic aspects of the physical environmental properties of the equipment.";
  }

  grouping holder-monitor-g {
    leaf is-active {
      type boolean;
      description
        "none";
    }
    leaf is-actual-mismatch-with-expected {
      type boolean;
      description
        "none";
    }
    leaf aggregate-function {
      type leafref {
        path "/core-model:aggregate-function/core-model:uuid";
      }
      description
        "none";
    }
    uses global-class-g;
    description
      "Represents the dynamic state of the holder instance. ";
  }

  grouping location-g {
    container equipment-location {
      uses address-g;
      description
        "none";
    }
    container geographical-location {
      uses address-g;
      description
        "none";
    }
    uses global-class-g;
    description
      "Represents where the equipment is.";
  }

  grouping equipment-structure-g {
    leaf category {
      type equipment-category;
      description
        "This attribute provides the identifier for a category of equipments regarded as having particular shared characteristics.";
    }
    description
      "Represents the form of the equipment.";
  }

  grouping equipment-instance-g {
    leaf manufacture-date {
      type string;
      description
        "This attribute represents the date on which this instance is manufactured.";
    }
    leaf serial-number {
      type string;
      description
        "This attribute represents the serial number of this instance.";
    }
    leaf asset-instance-identifier {
      type string;
      description
        "This attribute represents the asset identifier of this instance from the manufacturer's perspective.";
    }
    description
      "Represents the per instance invariant properties of the equipment.";
  }

  grouping equipment-type-g {
    leaf description {
      type string;
      description
        "none";
    }
    leaf model-identifier {
      type string;
      description
        "none";
    }
    leaf part-type-identifier {
      type string;
      description
        "none";
    }
    leaf type-name {
      type string;
      description
        "none";
    }
    leaf version {
      type string;
      description
        "none";
    }
    description
      "Represents the invariant properties of the equipment that define and characterize the type.";
  }

  grouping holder-structure-g {
    leaf holder-category {
      type holder-category;
      description
        "none";
    }
    leaf is-captive {
      type boolean;
      description
        "none";
    }
    leaf is-guided {
      type boolean;
      description
        "none";
    }
    leaf is-quantised-space {
      type boolean;
      description
        "none";
    }
    uses global-class-g;
    description
      "Represents the form of the holder.";
  }

  grouping manufactured-thing-g {
    leaf manufacturer-properties {
      type leafref {
        path "/core-model:manufacturer-properties/core-model:manufacturer-identifier";
      }
      description
        "none";
    }
    leaf equipment-type {
      type leafref {
        path "/core-model:equipment-type/core-model:model-identifier";
      }
      description
        "none";
    }
    leaf equipment-instance {
      type leafref {
        path "/core-model:equipment-instance/core-model:serial-number";
      }
      description
        "none";
    }
    leaf operator-augmented-equipment-type {
      type leafref {
        path "/core-model:operator-augmented-equipment-type/core-model:asset-type-identifier";
      }
      description
        "none";
    }
    leaf operator-augmented-equipment-instance {
      type leafref {
        path "/core-model:operator-augmented-equipment-instance/core-model:asset-instance-identifier";
      }
      description
        "none";
    }
    description
      "Collects all invariant aspects of a manufactured thing.";
  }

  grouping manufacturer-properties-g {
    leaf manufacturer-identifier {
      type string;
      description
        "none";
    }
    leaf manufacturer-name {
      type string;
      description
        "none";
    }
    description
      "Represents the properties of the manufacturer.";
  }

  grouping operator-augmented-equipment-type-g {
    leaf asset-type-identifier {
      type string;
      description
        "none";
    }
    description
      "Represents the invariant properties of the equipment asset allocated by the operator that define and characterize the type.";
  }

  grouping physical-characteristics-g {
    leaf weight-characeristics {
      type to-be-defined;
      description
        "none";
    }
    leaf fire-characteristics {
      type to-be-defined;
      description
        "none";
    }
    leaf materials {
      type to-be-defined;
      description
        "none";
    }
    uses global-class-g;
    description
      "Represents the invariant physical characteristics (including composition and physical robustness) of the type.";
  }

  grouping environmental-rating-g {
    leaf thermal-rating {
      type to-be-defined;
      description
        "This attribute represents the thermal characteristics (preferred maximum/minimum, absolute maximum/minimum etc) that the entity can tolerate.";
    }
    leaf power-rating {
      type to-be-defined;
      description
        "This attribute represents the power chracteristics (peak and mean per power source) of the entity.
         For an Equipment this is the power consumption.
         For  a Holder this is the power that can be conveyed.";
    }
    leaf humidity-rating {
      type to-be-defined;
      description
        "This attribute represents the humidity characteristics (preferred maximum/minimum, absolute maximum/minimum etc) that the entity can tolerate.";
    }
    uses global-class-g;
    description
      "Represents the invariant physical operational boundaries for the equipment/holder type.";
  }

  grouping position-g {
    leaf relative-position {
      type to-be-defined;
      description
        "none";
    }
    description
      "Represents the invariant relative position of the holder (with respect to some frame of reference in an equipment) or connector on an equipment or pin in a connector.";
  }

  grouping spatial-properties-of-type-g {
    leaf height {
      type to-be-defined;
      description
        "none";
    }
    leaf width {
      type to-be-defined;
      description
        "none";
    }
    leaf length {
      type to-be-defined;
      description
        "none";
    }
    uses global-class-g;
    description
      "Represents the basic invariant spatial properties of a physical thing.";
  }

  grouping swappability-g {
    leaf is-hot-swappable {
      type boolean;
      default "true";
      description
        "none";
    }
    uses global-class-g;
    description
      "Represents the degree of field replacement that is possible for the equipment type.";
  }

  grouping operator-augmented-equipment-instance-g {
    leaf asset-instance-identifier {
      type string;
      description
        "This attribute represents the asset identifier of this instance from the operator's perspective.";
    }
    description
      "Represents the invariant properties of the equipment asset allocated by the operator that define and characterize the type.";
  }

  grouping cable-g {
    leaf-list connector {
      type leafref {
        path "/core-model:connector/core-model:local-id";
      }
      min-elements 1;
      description
        "A connector that terminates the Cable to support the cable and/or allow signal flow into/out of the Cable.";
    }
    leaf manufactured-thing {
      type leafref {
        path "/core-model:manufactured-thing/core-model:equipment-instance";
      }
      description
        "none";
    }
    leaf physical-characteristics {
      type leafref {
        path "/core-model:physical-characteristics/core-model:uuid";
      }
      description
        "none";
    }
    leaf mechanical-features {
      type string;
      description
        "none";
    }
    leaf spatial-properties-of-type {
      type leafref {
        path "/core-model:spatial-properties-of-type/core-model:uuid";
      }
      description
        "none";
    }
    uses global-class-g;
    description
      "Basic model representing a cable with connectors fitted where the cable is 'short' (e.g.  patch cord, in-station cabling).
       This is intentionally a very basic representation of a cable. 
       In a more sophisticated representation cable ends might be represented that then associate to the attached connector. 
       At this point it is assumed that the basic model is sufficient.";
  }

  grouping connector-g {
    leaf-list pin {
      type leafref {
        path "/core-model:pin/core-model:position";
      }
      min-elements 1;
      description
        "none";
    }
    leaf orientation {
      type connector-and-pin-orientation;
      description
        "none";
    }
    leaf manufactured-thing {
      type leafref {
        path "/core-model:manufactured-thing/core-model:equipment-instance";
      }
      description
        "none";
    }
    leaf position {
      type string;
      description
        "none";
    }
    leaf mechanical-features {
      type string;
      description
        "none";
    }
    leaf pin-layout {
      type leafref {
        path "/core-model:pin-layout/core-model:uuid";
      }
      description
        "none";
    }
    leaf connector-type {
      type to-be-defined;
      description
        "none";
    }
    leaf role {
      type string;
      description
        "The purpose of the Connector in the physical space and the functional space.";
    }
    uses local-class-g;
    description
      "Represents a connector that may be fully exposed (e.g. to plug in a cable or on the end of a cable) or partially exposed (e.g. backplane to plug in another piece of equipment such as a module).
       A physical port on the Equipment. A place where signals produced by the functionality of the Equipment may be accessed.";
  }

  grouping equipment-g {
    leaf-list connector {
      type leafref {
        path "/core-model:connector/core-model:local-id";
      }
      description
        "A connector on the equipment.";
    }
    leaf-list contained-holder {
      type leafref {
        path "/core-model:holder/core-model:local-id";
      }
      description
        "References the Holder in an Equipment that is available to take other Equipments.
         For example:
         - Slot in a sub-rack
         - Slot in a Field Replaceable Unit that can take a small form-factor pluggable.";
    }
    leaf addressed-by-holder {
      type leafref {
        path "/core-model:holder/core-model:local-id";
      }
      description
        "none";
    }
    leaf-list encapsulated-non-fru {
      type leafref {
        path "/core-model:equipment/core-model:uuid";
      }
      description
        "An Equipment that is part of this Equipment and that is not separately field replaceable (i.e. will be field replaced with this Equipment).";
    }
    leaf-list exposed-cable {
      type leafref {
        path "/core-model:cable/core-model:uuid";
      }
      description
        "none";
    }
    leaf manufactured-thing {
      type leafref {
        path "/core-model:manufactured-thing/core-model:equipment-instance";
      }
      description
        "none";
    }
    leaf spatial-properties-of-type {
      type leafref {
        path "/core-model:spatial-properties-of-type/core-model:uuid";
      }
      description
        "none";
    }
    leaf mechanical-features {
      type string;
      description
        "none";
    }
    leaf physical-properties {
      type leafref {
        path "/core-model:physical-properties/core-model:uuid";
      }
      description
        "none";
    }
    leaf function-enablers {
      type leafref {
        path "/core-model:function-enablers/core-model:uuid";
      }
      description
        "none";
    }
    leaf mechanical-functions {
      type leafref {
        path "/core-model:mechanical-functions/core-model:uuid";
      }
      description
        "none";
    }
    leaf physical-characteristics {
      type leafref {
        path "/core-model:physical-characteristics/core-model:uuid";
      }
      description
        "none";
    }
    leaf swapability {
      type leafref {
        path "/core-model:swapability/core-model:uuid";
      }
      description
        "none";
    }
    leaf structure {
      type leafref {
        path "/core-model:equipment-structure/core-model:category";
      }
      description
        "none";
    }
    leaf environmental-rating {
      type leafref {
        path "/core-model:environmental-rating/core-model:uuid";
      }
      description
        "none";
    }
    leaf-list non-fru-support-position {
      type leafref {
        path "/core-model:non-fru-support-position/core-model:uuid";
      }
      description
        "none";
    }
    leaf is-field-replaceable {
      type boolean;
      default "true";
      config false;
      description
        "Indicates whether or not the equipment can be removed and replaced 'in the field' (i.e. in a deployment) by normal operations personnel. \n";
    }
    leaf-list function-block {
      type leafref {
        path "/core-model:function-block/core-model:uuid";
      }
      description
        "none";
    }
    leaf expected-equipment {
      type string;
      description
        "none";
    }
    leaf actual-equipment {
      type string;
      description
        "none";
    }
    leaf location {
      type leafref {
        path "/core-model:location/core-model:uuid";
      }
      description
        "none";
    }
    leaf-list foundation-pc {
      type leafref {
        path "/core-model:processing-construct/core-model:uuid";
      }
      description
        "Lowest level functional block with 1:1 to equipment.";
    }
    uses global-class-g;
    description
      "Represents any relevant physical thing. 
       Can be either field replaceable or not field replaceable.
       Note: The model is currently constrained to inside plant.";
  }

  grouping holder-g {
    leaf-list connector {
      type leafref {
        path "/core-model:connector/core-model:local-id";
      }
      description
        "The connector associated with a Holder of an Equipment.
         May represent connector on a backplane that takes Field Replaceable Units or a connector on a circuit pack that takes an SFP (Small Form-factor Pluggable).";
    }
    leaf occupying-fru {
      type leafref {
        path "/core-model:equipment/core-model:uuid";
      }
      description
        "The FRU that is occupying the holder. 
         A holder may be unoccupied. 
         An FRU may occupy more hat one holder (using or blocking are intentionally not distinguished here).";
    }
    leaf spatial-properties-of-type {
      type leafref {
        path "/core-model:spatial-properties-of-type/core-model:uuid";
      }
      description
        "none";
    }
    leaf-list holder-monitor {
      type leafref {
        path "/core-model:holder-monitor/core-model:uuid";
      }
      description
        "none";
    }
    container holder-location {
      uses address-g;
      description
        "none";
    }
    leaf position {
      type string;
      description
        "none";
    }
    leaf holder-structure {
      type leafref {
        path "/core-model:holder-structure/core-model:uuid";
      }
      description
        "none";
    }
    leaf environmental-rating {
      type leafref {
        path "/core-model:environmental-rating/core-model:uuid";
      }
      description
        "none";
    }
    leaf-list supported-equipment-type {
      type leafref {
        path "/core-model:equipment-type/core-model:model-identifier";
      }
      min-elements 1;
      description
        "An Equipment type that the Holder can accommodate (is compatible with).";
    }
    leaf expected-holder {
      type string;
      description
        "none";
    }
    leaf actual-holder {
      type string;
      description
        "none";
    }
    uses local-class-g;
    description
      "Represents a space in an equipment in which another equipment can be fitted in the field.";
  }

  typedef connector-and-pin-orientation {
    type identityref {
      base connector-and-pin-orientation;
    }
    description
      "Most connector schems are asymmetric such that there are two orientations of the connector where a mating is only possible between two connectors of different orientations. 
       A multi-pin connector may have a mix of pin orientations. In this case, it is expected that the dominant orientation of pin is chosen for the connector orientation.";
  }

  typedef equipment-category {
    type identityref {
      base equipment-category;
    }
    description
      "The form of equipment.";
  }

  typedef holder-category {
    type identityref {
      base holder-category;
    }
    description
      "The form of holder.";
  }

  grouping support-constraints-g {
    leaf-list constrained-supported-non-fru-type {
      type leafref {
        path "/core-model:supported-non-fru-type/core-model:uuid";
      }
      description
        "none";
    }
    leaf-list constrained-supported-fru-type {
      type leafref {
        path "/core-model:equipment-type/core-model:model-identifier";
      }
      description
        "none";
    }
    uses global-class-g;
    description
      "Rules related to how both non-FRU and FRU presence restricts the potential for additional equipments to be installed.
       An FRU type installed in one holder may limit the FRU types that can be installed in another holder etc.";
  }

  grouping supported-non-fru-type-g {
    leaf non-fru-details {
      type leafref {
        path "/core-model:equipment/core-model:uuid";
      }
      description
        "none";
    }
    leaf-list blocked-non-fru-position {
      type leafref {
        path "/core-model:non-fru-support-position/core-model:uuid";
      }
      min-elements 1;
      description
        "none";
    }
    leaf-list support-constraints {
      type leafref {
        path "/core-model:support-constraints/core-model:uuid";
      }
      description
        "none";
    }
    uses global-class-g;
    description
      "The non-FRU equipment types supported by the non-FRU support position.";
  }

  grouping non-fru-support-position-g {
    leaf-list supported-non-fru-type {
      type leafref {
        path "/core-model:supported-non-fru-type/core-model:uuid";
      }
      min-elements 1;
      description
        "none";
    }
    uses global-class-g;
    description
      "Equivalent to the holder for the FRU, represents in the specification a place where one or more types of non-FRU could be present. 
       Unlike the holder what is present is fixed whilst the equipment is in the field.";
  }

  grouping supported-equipment-type-g {
    leaf fru-details {
      type leafref {
        path "/core-model:equipment/core-model:uuid";
      }
      description
        "none";
    }
    leaf-list support-constraints {
      type leafref {
        path "/core-model:support-constraints/core-model:uuid";
      }
      description
        "none";
    }
    leaf-list holder {
      type leafref {
        path "/core-model:holder/core-model:local-id";
      }
      min-elements 1;
      description
        "none";
    }
    description
      "The FRU equipment types supported by the holder.";
  }

  grouping pin-g {
    leaf position {
      type string;
      description
        "none";
    }
    leaf orientation {
      type connector-and-pin-orientation;
      description
        "none";
    }
    description
      "An individual physical connection point (male or female) that is not relevantly divisible.
       May be capable of carrying electrical or optical signals. 
       A pin normally has only one wire/fiber strand attached. 
       It may have more than one wire/fiber attached but is such that the attachment forms a physical merge (all attached things receive exactly the same signal and any inputs to the pin are electrically/optically merged).";
  }

  grouping pin-group-g {
    leaf-list pin {
      type leafref {
        path "/core-model:pin/core-model:position";
      }
      min-elements 1;
      description
        "none";
    }
    uses global-class-g;
    description
      "A group of pins that together provide signal group where any one pin removed from the group will prevent the signals of the signal group from flowing successfully.";
  }

  grouping pin-layout-g {
    leaf position {
      type string;
      description
        "none";
    }
    uses global-class-g;
    description
      "The structuring of pins in a connector.";
  }

  grouping signal-ref-pt-g {
    leaf ltp {
      type leafref {
        path "/core-model:logical-termination-point/core-model:uuid";
      }
      description
        "none";
    }
    leaf-list elemental-signals {
      type leafref {
        path "/core-model:elemental-signals/core-model:uuid";
      }
      min-elements 1;
      description
        "none";
    }
    description
      "A single coherent signal as processed by a single LTP.";
  }

  grouping signal-ref-pt-group-g {
    leaf pin-group {
      type leafref {
        path "/core-model:pin-group/core-model:uuid";
      }
      description
        "none";
    }
    leaf-list signal-ref-pt {
      type leafref {
        path "/core-model:signal-ref-pt/core-model:ltp";
      }
      min-elements 1;
      description
        "none";
    }
    uses global-class-g;
    description
      "A physical indivisible group of signals.";
  }

  grouping elemental-signals-g {
    leaf-list pin {
      type leafref {
        path "/core-model:pin/core-model:position";
      }
      min-elements 1;
      description
        "none";
    }
    uses global-class-g;
    description
      "The elemental (sub-atomic) parts of an 'indivisible' signal where processing in the LTP is required to extract the elemental signals.";
  }

  grouping aggregate-function-g {
    leaf-list atomic-function {
      type leafref {
        path "/core-model:atomic-function/core-model:uuid";
      }
      description
        "none";
    }
    leaf-list function-block {
      type leafref {
        path "/core-model:function-block/core-model:uuid";
      }
      description
        "none";
    }
    leaf-list atomic-function-view {
      type leafref {
        path "/core-model:atomic-function/core-model:uuid";
      }
      description
        "none";
    }
    uses global-class-g;
    description
      "Represents some assembly of atomic functions that can be considered as useful from some perspective. Can be viewed as one or more functional blocks (essential leading to a recursive cycle of Block --> Atomic --> Aggregate --> Block). 
       Each of the functional entities in the model is a view of a single AggregateFunction.";
  }

  grouping atomic-function-g {
    leaf-list aggregate-function {
      type leafref {
        path "/core-model:aggregate-function/core-model:uuid";
      }
      description
        "none";
    }
    uses global-class-g;
    description
      "Represents the micro-function that is the largest function of the functional block that will not need to be subdivided when forming the relevant abstract views (i.e., it can just be assembled).";
  }

  grouping function-block-g {
    leaf-list atomic-function {
      type leafref {
        path "/core-model:atomic-function/core-model:uuid";
      }
      description
        "none";
    }
    leaf-list equipment {
      type leafref {
        path "/core-model:equipment/core-model:uuid";
      }
      description
        "none";
    }
    uses global-class-g;
    description
      "Represents the chunks of base functionality provided by the equipment.
       The chunks of base functionality are likely to relate to the hardware layout and be quite distinct from the functions of the familiar abstract representation.
       The functions are necessarily abstract and, to a degree, virtualized.";
  }

  grouping resilient-function-block-g {
    leaf-list atomic-function {
      type leafref {
        path "/core-model:atomic-function/core-model:uuid";
      }
      description
        "none";
    }
    uses global-class-g;
    description
      "Represents the functions emergent from a function protection process.
       The emergent functions are necessarily significantly virtualized.";
  }

  grouping resilience-selector-g {
    leaf resilient-function-block {
      type leafref {
        path "/core-model:resilient-function-block/core-model:uuid";
      }
      description
        "none";
    }
    leaf-list function-block {
      type leafref {
        path "/core-model:function-block/core-model:uuid";
      }
      min-elements 2;
      description
        "none";
    }
    description
      "Represents the ability to select capability from two or more identical FunctionalBlocks so as to give rise to an equivalent emergent resilient function.";
  }

  grouping configuration-and-switch-controller-spec-g {
    leaf-list switch-control-rule {
      type leafref {
        path "/core-model:control-rule/core-model:local-id";
      }
      min-elements 1;
      description
        "none";
    }
    leaf-list ingress-switch-selection {
      type string;
      description
        "none";
    }
    leaf-list egress-switch-selection {
      type string;
      description
        "none";
    }
    uses global-class-g;
    description
      "The spec of a ConfigurationAndSwitchController.";
  }

  grouping egress-port-set-g {
    uses local-class-g;
    description
      "The grouping of FC egress ports that have the same behavior and relationship to the switch etc.
       Will carry rules for the grouping.";
  }

  grouping forwarding-spec-g {
    leaf-list multi-switched-uni-flow {
      type leafref {
        path "/core-model:multi-switched-uni-flow/core-model:local-id";
      }
      min-elements 1;
      description
        "none";
    }
    leaf-list casc-spec {
      type leafref {
        path "/core-model:configuration-and-switch-control/core-model:switch-rule";
      }
      description
        "none";
    }
    leaf-list port-set-spec {
      type leafref {
        path "/core-model:port-set-spec/core-model:local-id";
      }
      min-elements 1;
      description
        "none";
    }
    leaf configuration-group-spec-spec {
      type leafref {
        path "/core-model:configuration-group-spec/core-model:uuid";
      }
      description
        "none";
    }
    leaf ltp-association-rule {
      type leafref {
        path "/core-model:ltp-association-rule/core-model:local-id";
      }
      description
        "none";
    }
    leaf-list layer-protocol-parameter-spec {
      type string;
      description
        "none";
    }
    leaf-list subordinate-forwarding {
      type string;
      description
        "none";
    }
    leaf-list component-ltp {
      type string;
      description
        "none";
    }
    leaf spec-target-class {
      type metaclass-class-name;
      description
        "
         range of type : Link, ForwardingConstruct";
    }
    uses global-class-g;
    description
      "The overall spec for the forwarding entity.";
  }

  grouping ingress-port-set-g {
    uses local-class-g;
    description
      "The grouping of FC ingress ports that have the same behavior and relationship to the switch etc.
       Will carry rules for the grouping.";
  }

  grouping multi-switched-uni-flow-g {
    leaf-list ingress-port-set {
      type leafref {
        path "/core-model:ingress-port-set/core-model:local-id";
      }
      min-elements 1;
      description
        "none";
    }
    leaf-list egress-port-set {
      type leafref {
        path "/core-model:egress-port-set/core-model:local-id";
      }
      min-elements 1;
      description
        "none";
    }
    leaf casc {
      type leafref {
        path "/core-model:configuration-and-switch-control/core-model:switch-rule";
      }
      description
        "none";
    }
    leaf ingress-fc-port-set {
      type leafref {
        path "/core-model:ingress-port-set/core-model:local-id";
      }
      description
        "none";
    }
    leaf egress-fc-port-set {
      type leafref {
        path "/core-model:egress-port-set/core-model:local-id";
      }
      description
        "none";
    }
    leaf layer-protocol-parameter-spec {
      type string;
      description
        "none";
    }
    uses local-class-g;
    description
      "A switched unidirectional forwarding element that can take one or more inputs and switch to one or more outputs.
       The switch can also be open (high impedance).";
  }

  grouping port-set-spec-g {
    leaf-list ingress-port-set {
      type leafref {
        path "/core-model:ingress-port-set/core-model:local-id";
      }
      description
        "none";
    }
    leaf-list egress-port-set {
      type leafref {
        path "/core-model:egress-port-set/core-model:local-id";
      }
      description
        "none";
    }
    leaf ltp-association-rule {
      type leafref {
        path "/core-model:ltp-association-rule/core-model:local-id";
      }
      description
        "none";
    }
    leaf role {
      type string;
      default "true";
      description
        "Role of the port in the context of the ForwardingSpec.";
    }
    leaf layer-protocol-parameter-spec {
      type string;
      description
        "none";
    }
    leaf is-internal-port {
      type boolean;
      config false;
      description
        "The FcPort is not exposed and cannot have associated LTPs.
         This form of FcPort is used to enable chaining of FcSwitches or FcRoutes in complex network protection scenarios.";
    }
    leaf client-side-of-ltp {
      type string;
      description
        "none";
    }
    leaf server-side-of-ltp {
      type string;
      description
        "none";
    }
    uses local-class-g;
    description
      "The specification a set of equivalent port of the forwarding entity.";
  }

  grouping configuration-group-spec-g {
    leaf casc {
      type leafref {
        path "/core-model:configuration-and-switch-control/core-model:switch-rule";
      }
      description
        "none";
    }
    leaf-list forwarding-spec {
      type leafref {
        path "/core-model:forwarding-spec/core-model:spec-target-class";
      }
      min-elements 1;
      description
        "none";
    }
    leaf ltp-association-rule {
      type leafref {
        path "/core-model:ltp-association-rule/core-model:local-id";
      }
      description
        "none";
    }
    uses global-class-g;
    description
      "The specification of the grouping rules for a particular configuration of FCs and CASCs.";
  }

  grouping control-rule-g {
    uses local-class-g;
    description
      "A rule describes the bounds of the behavior of a CASC.";
  }

  grouping ltp-association-rule-g {
    uses local-class-g;
    description
      "Rules for the association from the port spec to LTPs identifying restrictions of use.";
  }

  grouping fd-and-link-rule-g {
    leaf rule-type {
      type rule-type;
      description
        "Indicates how to interpret the rule statements.";
    }
    leaf forwarding-rule {
      type forwarding-rule;
      description
        "none";
    }
    leaf-list complex-rule-qualifier {
      type to-be-defined;
      description
        "complexRuleQualifier is used to modulate the rule.
         complexRuleQualifier covers case such as same channel but can reference any property of the FD, of the associated LTP and of the FC instance to be created.
         Qualifier should be capable of expressing rule interaction.
         Provides restrictions (such as same channel).
         Note: May be better to have a same index/any index explicit rule.
         Could have 'property=x' valueEquation=same, increment, etc.'";
    }
    leaf fc-spec {
      type to-be-defined;
      description
        "Indicates the type(s) of FC to which the rule applies.";
    }
    list fc-port-role {
      key "uuid";
      uses port-role-rule-g;
      description
        "Indicates the port role to which the rule applies. 
         If an FD carries a port role that role applies also to the associated Link rules.
         fcPortRole corresponded to role defined in the FcSpec. This is a list with rule opportunity. No port role statement means all port roles are allowed.";
    }
    leaf-list fc-port-direction {
      type port-direction;
      description
        "fcPortDirection is a list of FcPortDirection.";
    }
    leaf override-priority {
      type uint64;
      description
        "overridePriority allows for one rule set to override another.";
    }
    container signal-property {
      uses signal-property-rule-g;
      description
        "none";
    }
    list fc-spec-reference-class-ref {
      if-feature "_ugmw0mGYEeerc4Zz6ufSeg";
      key "name";
      uses metaclass-class-g;
      description
        "none";
    }
    uses global-class-g;
    description
      "Set of 'AND' rules related to creation of FCs across the FD/Link (i.e., all rules have to be met for the FC creation to be allowed).
       Embedded conditions all have to be met and hence are AND. Elements of the list attributes are ORs.
       Absence fcSpec NOT valid for FORWARDING rules (only valid for cost/risk etc. rules).
       Absence of FcPortRole means all roles for referenced spec.
       Absence of direction means all directions.";
  }

  grouping fd-and-link-rule-set-g {
    leaf-list fd-rule {
      type leafref {
        path "/core-model:fd-and-link-rule/core-model:uuid";
      }
      min-elements 1;
      description
        "none";
    }
    leaf is-rule-only {
      type boolean;
      description
        "Indicates that the FD is only carrying rules and that FC creation is the FD is NOT allowed.";
    }
    uses global-class-g;
    description
      "Set of 'OR' rules related to creation of FCs across the FD/Link (i.e. only one of the rules have to be met for the FC creation to be allowed).
       Absence of RuleSet means 'Any', i.e. all points, all FcTypes etc.
       Presence of RuleSet means possibilities must all be defined by rules
       Absence of forwardingRule means no explicit stated possibilities.
       No capacity statement means no capacity restrictions.
      ";
  }

  feature _ugmw0mGYEeerc4Zz6ufSeg {
    description
      "specTargetClass=ForwardingConstruct";
  }

  typedef forwarding-rule {
    type identityref {
      base forwarding-rule;
    }
    description
      "Rule that restricts the creation/deletion of an FC between points grouped by FD or related by the Link between FDs.";
  }

  typedef rule-type {
    type identityref {
      base rule-type;
    }
    description
      "Indicates the focus of the rule.";
  }

  grouping port-role-rule-g {
    leaf-list port-role {
      type port-role;
      description
        "none";
    }
    leaf-list port-role-rule {
      type port-role-rule;
      description
        "none";
    }
    uses global-class-g;
    description
      "none";
  }

  typedef port-role-rule {
    type identityref {
      base port-role-rule;
    }
    description
      "none";
  }

  grouping signal-property-rule-g {
    leaf signal-property-name {
      type string;
      description
        "none";
    }
    leaf signal-property-value-rule {
      type signal-property-value-rule;
      description
        "none";
    }
    leaf-list applicable-signal-value {
      type string;
      description
        "none";
    }
    description
      "none";
  }

  typedef signal-property-value-rule {
    type identityref {
      base signal-property-value-rule;
    }
    description
      "none";
  }

  grouping metaclass-class-g {
    leaf name {
      type metaclass-class-name;
      description
        "The text name of the Class";
    }
    description
      "This datatype represents the '<<Metaclass>> Class' from the UML metamodel. 
       An instance of the referencing Class (e.g. LTP) will reference a Class (not an instance).
       This referenced Class will provide definition to extend the referencing instance. 
       So, for example, an LTP instance will have the attributes defined in the LTP class and also the attributes defined in the referenced Class (an LtpSpec).
       The referenced Class may:
       (1) provide invariant properties (that are the same for many instances) that then are not conveyed with the referencing instance.
       (2) provide definitions for attributes that are present in the instance that are not defined in the Class of the instance (these attribute may have been pruned and refactored from one or more external definition sources). 
       (3) apply constraints to attributes in the instance that were defined in the class of the referencing instance.
       (4) replace attributes that were present in the class of the referencing instance by a new definition (same name).
      ";
  }

  typedef metaclass-class-name {
    type string;
    description
      "none";
  }

  grouping composed-part-g {
    list part-spec-reference-class-ref {
      if-feature "_axGsoWIiEeerc4Zz6ufSeg";
      key "name";
      min-elements 1;
      uses metaclass-class-g;
      description
        "none";
    }
    uses global-class-g;
    description
      "none";
  }

  grouping entity-g {
    leaf-list extension-container {
      type leafref {
        path "/core-model:extension-container/core-model:uuid";
      }
      description
        "none";
    }
    leaf-list composed-part {
      type leafref {
        path "/core-model:composed-part/core-model:uuid";
      }
      description
        "none";
    }
    list entity-spec-reference-class-ref {
      if-feature "_dif9kGIfEeerc4Zz6ufSeg";
      key "name";
      min-elements 1;
      uses metaclass-class-g;
      description
        "none";
    }
    description
      "none";
  }

  grouping entity-spec-g {
    leaf-list part-spec {
      type leafref {
        path "/core-model:part-spec/core-model:spec-target-class";
      }
      description
        "none";
    }
    leaf spec-target-class {
      type metaclass-class-name;
      description
        "
         range of type : Entity, Entity/ExtensionContainer";
    }
    description
      "none";
  }

  grouping extension-container-g {
    list entity-spec-reference-class-ref {
      if-feature "_6ou3cGIgEeerc4Zz6ufSeg";
      key "name";
      min-elements 1;
      uses metaclass-class-g;
      description
        "none";
    }
    uses global-class-g;
    description
      "none";
  }

  grouping part-spec-g {
    leaf spec-target-class {
      type metaclass-class-name;
      description
        "
         range of type : Entity/ComposedPart";
    }
    description
      "none";
  }

  feature _axGsoWIiEeerc4Zz6ufSeg {
    description
      "specTargetClass=Entity/ComposedPart";
  }

  feature _dif9kGIfEeerc4Zz6ufSeg {
    description
      "specTargetClass=Entity";
  }

  feature _6ou3cGIgEeerc4Zz6ufSeg {
    description
      "specTargetClass=Entity/ExtensionContainer";
  }

  grouping control-component-g {
    leaf-list control-system-view {
      type leafref {
        path "/core-model:control-system-view/core-model:uuid";
      }
      description
        "none";
    }
    leaf-list defining-view-mapping {
      type leafref {
        path "/core-model:view-mapping/core-model:uuid";
      }
      min-elements 1;
      description
        "ControlComponent behavior is defined in part by view mappings.";
    }
    leaf-list control-port {
      type leafref {
        path "/core-model:control-port/core-model:uuid";
      }
      description
        "none";
    }
    leaf-list subordinate-control-component-view {
      type leafref {
        path "/core-model:control-component/core-model:uuid";
      }
      description
        "A ControlComponent that is part of an abstract view of the system that supports the referencing ControlComponent and hence describes part of the behavior of the referencing ControlComponent.";
    }
    leaf-list view-mapping {
      type leafref {
        path "/core-model:view-mapping/core-model:uuid";
      }
      description
        "ControlComponent uses the referenced ViewMapping to produce one view from another.";
    }
    uses global-class-g;
    description
      "Represents control capability/functionality. The functionality is emergent from the running software.
       ControlComponents communicate with other ControlComponents through ControlPorts about things expressed in the corresponding ControlSystemViews.
       Examples of higher level aggregate ControlComponents are:
       - the controller in the Network/Managed Element e.g. an SNMP agent).
       - an SDN Controller.
       - an EMS.
       - an NMS.
       Examples of lower level ControlComponents are:
       - Path Computation.
       - Problem Analytics.
       This specific model follows a subset of the Component-System Pattern as that is all that is necessary for this aspect of expression. 
      ";
  }

  grouping control-port-g {
    leaf-list protecting-control-port {
      type leafref {
        path "/core-model:control-port/core-model:uuid";
      }
      description
        "A simple representation of resilience where one ControlPorts are identified as providing equivalent information.";
    }
    leaf control-port {
      type leafref {
        path "/core-model:control-port/core-model:uuid";
      }
      description
        "Control Ports may be used to associate controllers in a hierarch and as peers.
         Peer controllers are assumed to both the subordinate of each other.";
    }
    leaf ltp {
      type leafref {
        path "/core-model:logical-termination-point/core-model:uuid";
      }
      description
        "The LTP through which the control messaging/signaling flows.";
    }
    uses global-class-g;
    description
      "The access to the ControlComponent following the normal Component-Port pattern (i.e. the functions of a component are accessed via ports).
       Is assumed to usually be bidirectional.";
  }

  grouping control-system-view-g {
    leaf-list ltp {
      type leafref {
        path "/core-model:logical-termination-point/core-model:uuid";
      }
      description
        "LTP in ControlSystemView";
    }
    leaf-list fd {
      type leafref {
        path "/core-model:forwarding-domain/core-model:uuid";
      }
      description
        "FD in ControlSystemView";
    }
    leaf-list link {
      type leafref {
        path "/core-model:link/core-model:uuid";
      }
      description
        "Link in ControlSystemView";
    }
    leaf-list fc {
      type leafref {
        path "/core-model:forwarding-construct/core-model:uuid";
      }
      description
        "FC in ControlSystemView";
    }
    leaf-list pc {
      type leafref {
        path "/core-model:processing-construct/core-model:uuid";
      }
      description
        "PC in ControlSystemView";
    }
    leaf-list cd {
      type leafref {
        path "/core-model:constraint-domain/core-model:uuid";
      }
      description
        "CD in ControlSystemView";
    }
    leaf-list equipment {
      type leafref {
        path "/core-model:equipment/core-model:uuid";
      }
      description
        "Equipment in ControlSystemView";
    }
    leaf-list subordinate-control-system-view {
      type leafref {
        path "/core-model:control-system-view/core-model:uuid";
      }
      description
        "A ControlSystemView that is a subset of this ControlSystemView providing more detail.";
    }
    leaf-list control-port {
      type leafref {
        path "/core-model:control-port/core-model:uuid";
      }
      description
        "Port of ControlComponent through which the referencing ControlSystemView is accessed.";
    }
    leaf-list control-component {
      type leafref {
        path "/core-model:control-component/core-model:uuid";
      }
      description
        "A ControlComponent (subordinate) that is in this ControlSystemView (superior) which was provided by another ControlComponent (superior). 
         The ControlComponent (subordinate) will have exposed its own ControlSystemViews (original subordinate).
         These ControlSystemViews (original subordinate) will be pruned and refactored by the ControlComponent (superior) to be presented in the ControlSystemView (superior) under the view of the ControlComponent (subordinate) as a ControlSystemView (pruned and refactored subordinate).
         The ControlSystemView (pruned and refactored subordinate) will have other components represented that may include ControlComponents. The process is recursive.
        ";
    }
    uses global-class-g;
    description
      "A view of the things controlled by a control system.
       A ControlSystemView is structured presentation of the underlying controlled things (the 'actual' entities) for some purpose.
       The ControlSystemView is constructed by pruning and refactoring the models of the underlying controlled things.
       Is an aggregation of 'views of things' where a 'view of things' is represented in abstraction by an Object Class in the model.
       The ControlComponent is itself controlled and presents itself in terms of ControlComponents (subordinate) in a view.
       At one extreme a ControlSystemView may expose all underlying details of everything controlled with no adjustment from the presentation provided by the controlled things.
       A ControlSystemView may expose a subset of the controlled things that focuses on a particular aspect (e.g. only the ControlComponents).";
  }

  grouping view-mapping-g {
    leaf-list controller-internal-view {
      type string;
      min-elements 1;
      max-elements "2";
      description
        "none";
    }
    leaf-list control-system-view {
      type leafref {
        path "/core-model:control-system-view/core-model:uuid";
      }
      min-elements 2;
      max-elements "2";
      description
        "none";
    }
    uses global-class-g;
    description
      "The rules that relate one view to another.";
  }

  grouping processing-construct-g {
    leaf-list equipment {
      type leafref {
        path "/core-model:equipment/core-model:uuid";
      }
      description
        "The Equipment(s) that support the functionality of the PC.
         This attribute is meaningful at the lowest level of PC recursion where the PC is supported by a single piece of Equipment.
         At higher levels, the supporting equipment may be more difficult to evaluate especially where there is resilience and/or virtualization of some form.
         This attribute allows diagnostics and engineering works impact evaluation.
         In an implementation, the information may be acquired via a query on the equipment that exposes this reverse association. ";
    }
    leaf-list pc-port {
      type leafref {
        path "/core-model:pc-port/core-model:local-id";
      }
      description
        "An asymmetric PC instance is related to LTPs via PcPorts (essentially the ports of the PC). 
         Symmetric PCs don't have PcPorts and are directly related to LTPs.";
    }
    leaf-list ltp {
      type leafref {
        path "/core-model:logical-termination-point/core-model:uuid";
      }
      description
        "A symmetric PC instance is associated with zero or more LTP objects.  
         The LTPs on the PC boundary provide information for processing and capacity for communication. 
         For asymmetric PCs the association to the LTP is via the PcPort (with stated role, allowing access to a specific function of the PC).";
    }
    leaf-list cd {
      type leafref {
        path "/core-model:constraint-domain/core-model:uuid";
      }
      description
        "One or more ConstraintDomains can constrain a ProcessingConstruct. 
         A constrained PC connects LTPs on the boundary of the CD.";
    }
    leaf-list fd {
      type leafref {
        path "/core-model:forwarding-domain/core-model:uuid";
      }
      description
        "One or more ForwardingDomains can constrain a ProcessingConstruct. 
         A constrained PC connects LTPs on the boundary of the FD.";
    }
    leaf-list composed-pc {
      type leafref {
        path "/core-model:processing-construct/core-model:uuid";
      }
      description
        "The PC class supports a recursive aggregation relationship (PcIsAssemblyOfPc).
         This allows both:
         - abstraction where an assembly of PCs (forming a System) is viewed as an abstract PC
         - decomposition such that the internal construction of a PC can be exposed as multiple lower level PCs. 
         Appropriate use of this association allows each of a collection of PCs to be decomposed into atomic parts (PCs) that can then be assembled into set of complex functions where each function in the set can be viewed as a PC.
         Note that the model actually represents an aggregation of lower level PCs into higher level PCs as viewpoints rather than partitions, and supports multiple views.";
    }
    leaf pc-resilience-selector {
      type leafref {
        path "/core-model:pc-resilience-selector/core-model:local-id";
      }
      description
        "PcResilienceSelector that realizes the resilience of the PC.";
    }
    uses global-class-g;
    description
      "ProcessingConstruct (PC) can be used to represent both potential and enabled processing between two or more of its PcPorts.
       A PcPort may be associated with another PcPort or with an LTPs at a particular specific layerProtocol. 
       Like the LTP, the PC supports any transport protocol including all circuit and packet forms. 
       The PC is used to effect processing of information extracted from the transport layer protocol signal. 
       A PC may be:
       - Asymmetric such that it offers several function sans such that different functions are offered to different attached entities. 
       - Symmetric such that it offers (or is considered as offering) only on function and the same function is offered to any attached entity with no interactions between functions offered to each attached entity
       An asymmetric PC offerning a number of distinct functions will have PcPorts through which the distinct functions are accessed.
       A symmetric PC offering only a single function need not have PcPorts, the function can be accessed directly from the PC. ";
  }

  grouping cd-port-g {
    leaf cd-port {
      type leafref {
        path "/core-model:cd-port/core-model:local-id";
      }
      description
        "Constraint Domains can be meshed together view their ports directly as well as via LTPs indirectly.\n";
    }
    leaf-list ltp {
      type leafref {
        path "/core-model:logical-termination-point/core-model:uuid";
      }
      max-elements "2";
      description
        "A CdPort is associated with zero or more LTP objects.  
         The LTPs on the CD boundary provide capacity for processing. 
         For symmetric CDs the association is directly from the CD to the LTP.";
    }
    leaf-list pc-port {
      type leafref {
        path "/core-model:pc-port/core-model:local-id";
      }
      description
        "Where a CD is asymmetric and hence has CdPorts and where that CD  supports PCs, appropriate CdPorts of that CD support the corresponding PcPorts.";
    }
    uses local-class-g;
    description
      "The association of the CD to LTPs is direct for symmetric CDs and via CdPort for asymmetric CDs. 
       The CdPort class models role based access to a CD.  
       The capability to set up PCs between the associated CdPorts of a CD depends upon the type of CD. 
       It is asymmetry in this capability that brings the need for CdPort.   
       The CD can be considered as a component and the CdPort as a Port on that component.";
  }

  grouping constraint-domain-g {
    leaf-list cd-port {
      type leafref {
        path "/core-model:cd-port/core-model:local-id";
      }
      description
        "An asymmetric CD instance is related to LTPs via CdPorts (essentially the ports of the CD). 
         Symmetric CDs don't have CdPorts and are directly related to LTPs.";
    }
    leaf-list pc {
      type leafref {
        path "/core-model:processing-construct/core-model:uuid";
      }
      description
        "A CD constrains one or more PCs. 
         A constrained PC connects LTPs that are on the CD boundary.";
    }
    leaf ltp {
      type leafref {
        path "/core-model:logical-termination-point/core-model:uuid";
      }
      description
        "A symmetric CD instance is associated with zero or more LTP objects.  
         The LTPs on  the CD boundary provide capacity for processing. 
         For asymmetric FDs the association to the LTP is via the FdPort.";
    }
    leaf-list composed-cd {
      type leafref {
        path "/core-model:constraint-domain/core-model:uuid";
      }
      description
        "The CD class supports a recursive aggregation relationship (CdEncompassesCd) such that the internal construction of an CD can be exposed as multiple lower level CDs. 
         Note that the model actually represents an aggregation of lower level CDs into higher level CDs as viewpoints rather than partitions, and supports multiple views";
    }
    leaf-list casc {
      type leafref {
        path "/core-model:configuration-and-switch-control/core-model:switch-rule";
      }
      description
        "A controller operating in the scope defined.";
    }
    leaf-list equipment {
      type leafref {
        path "/core-model:equipment/core-model:uuid";
      }
      description
        "A ConstraintDomain can be used to represent physical constraints in the logical view. 
         In this case the CD can be associated to the physical equipment.";
    }
    leaf-list fc {
      type leafref {
        path "/core-model:forwarding-construct/core-model:uuid";
      }
      description
        "A CD constrains one or more FCs. 
         A constrained FC connects LTPs that are on the CD boundary.";
    }
    leaf-list fd {
      type leafref {
        path "/core-model:forwarding-domain/core-model:uuid";
      }
      description
        "A CD constrains one or more FDs. 
         A constrained FD connects LTPs that are on the CD boundary.";
    }
    uses global-class-g;
    description
      "ConstraintDomain (CD) models the topological component that represents the opportunity to enable processing of information between two or more of its CdPorts.
       A CdPort may be associated with another CdPort or with an LTPs at a particular specific layerProtocol. 
       It provides the context for and constrains the formation, adjustment and removal of PCs and hence offers the potential to enable processing.  
       The LTPs available are those defined at the boundary of the CD. 
       CD can also be considered as the container of a view.
       A CD may be:
       - Asymmetric such that it offers several function sans such that different functions are offered to different attached entities. 
       - Symmetric such that it offers (or is considered as offering) only on function and the same function is offered to any attached entity with no interactions between functions offered to each attached entity
       An asymmetric CD offerning a number of distinct functions will have CdPorts through which the distinct functions are accessed.
       A symmetric CD offering only a single function need not have CdPorts, the function can be accessed directly from the CD.";
  }

  grouping pc-port-g {
    leaf-list ltp {
      type leafref {
        path "/core-model:logical-termination-point/core-model:uuid";
      }
      max-elements "2";
      description
        "A PC instance is associated with zero or more LTP objects.  
         The LTPs on the PC boundary provide capacity for processing. 
         For asymmetric PCs the association to the LTP is via the PcPort.";
    }
    leaf-list pc-port {
      type leafref {
        path "/core-model:pc-port/core-model:local-id";
      }
      max-elements "2";
      description
        "A PcPort can be directly bound to another PcPort (rather than via a LTP) to support a simplified application level view (rather than requiring the full transport level view).";
    }
    leaf-list fc-port {
      type leafref {
        path "/core-model:forwarding-construct/core-model:fc-port/core-model:local-id";
      }
      max-elements "2";
      description
        "A PcPort can be directly bound to an FcPort (rather than via a LTP) to support a simplified application level view (rather than requiring the full transport level view). 
         This is used to represent complex semantic associations between PCs where _pcPort direct association is not sufficient.";
    }
    leaf port-role {
      type string;
      description
        "Identifies the role of the port in the context of the specification of the PC.";
    }
    uses local-class-g;
    description
      "Represents the access to the functionality of a PC.";
  }

  grouping pc-resilience-selector-g {
    leaf-list pc {
      type leafref {
        path "/core-model:processing-construct/core-model:uuid";
      }
      min-elements 2;
      description
        "Alternative PC.";
    }
    uses local-class-g;
    description
      "Rudimentary resilience model for PC.";
  }

  container control-component {
    uses control-component-g;
    description
      "none";
  }
  list aggregate-function {
    key "uuid";
    uses aggregate-function-g;
    description
      "none";
  }
  list atomic-function {
    key "uuid";
    uses atomic-function-g;
    description
      "none";
  }
  list cable {
    key "uuid";
    uses cable-g;
    description
      "none";
  }
  list casc-port {
    key "uuid";
    uses casc-port-g;
    description
      "none";
  }
  list casc-port-role-properties {
    key "uuid";
    uses casc-port-role-properties-g;
    description
      "none";
  }
  list composed-part {
    key "uuid";
    uses composed-part-g;
    description
      "none";
  }
  list configuration-and-switch-controller-spec {
    key "uuid";
    uses configuration-and-switch-controller-spec-g;
    description
      "none";
  }
  list configuration-group-spec {
    key "uuid";
    uses configuration-group-spec-g;
    description
      "none";
  }
  list constraint-domain {
    key "uuid";
    uses constraint-domain-g;
    description
      "none";
  }
  list control-parameters {
    key "uuid";
    uses control-parameters-pac-g;
    description
      "none";
  }
  list control-port {
    key "uuid";
    uses control-port-g;
    description
      "none";
  }
  list control-system-view {
    key "uuid";
    uses control-system-view-g;
    description
      "none";
  }
  list desired-outcome-constraints {
    key "uuid";
    uses desired-outcome-constraints-g;
    description
      "none";
  }
  list environmental-rating {
    key "uuid";
    uses environmental-rating-g;
    description
      "none";
  }
  list equipment {
    key "uuid";
    uses equipment-g;
    description
      "none";
  }
  list element-constraints {
    key "uuid";
    uses element-constraints-g;
    description
      "none";
  }
  list elemental-signals {
    key "uuid";
    uses elemental-signals-g;
    description
      "none";
  }
  list extension-container {
    key "uuid";
    uses extension-container-g;
    description
      "none";
  }
  list fc-route {
    key "uuid";
    uses fc-route-g;
    description
      "none";
  }
  list fd-and-link-rule {
    key "uuid";
    uses fd-and-link-rule-g;
    description
      "none";
  }
  list fd-and-link-rule-set {
    key "uuid";
    uses fd-and-link-rule-set-g;
    description
      "none";
  }
  list forwarding-construct {
    key "uuid";
    uses forwarding-construct-g;
    description
      "none";
  }
  list forwarding-domain {
    key "uuid";
    uses forwarding-domain-g;
    description
      "none";
  }
  list forwarding-spec {
    key "uuid";
    uses forwarding-spec-g;
    description
      "none";
  }
  list function-block {
    key "uuid";
    uses function-block-g;
    description
      "none";
  }
  list function-enablers {
    key "uuid";
    uses function-enablers-g;
    description
      "none";
  }
  list holder-monitor {
    key "uuid";
    uses holder-monitor-g;
    description
      "none";
  }
  list holder-structure {
    key "uuid";
    uses holder-structure-g;
    description
      "none";
  }
  list lifecycle-scoping-class {
    key "uuid";
    uses lifecycle-scoping-class-g;
    description
      "none";
  }
  list link {
    key "uuid";
    uses link-g;
    description
      "none";
  }
  list location {
    key "uuid";
    uses location-g;
    description
      "none";
  }
  list logical-termination-point {
    key "uuid";
    uses logical-termination-point-g;
    description
      "none";
  }
  list name-and-value-authority {
    key "uuid";
    uses name-and-value-authority-g;
    description
      "none";
  }
  list mechanical-functions {
    key "uuid";
    uses mechanical-functions-g;
    description
      "none";
  }
  list non-fru-support-position {
    key "uuid";
    uses non-fru-support-position-g;
    description
      "none";
  }
  list necessary-initial-condition-constraints {
    key "uuid";
    uses necessary-initial-condition-constraints-g;
    description
      "none";
  }
  list operation-details {
    key "uuid";
    uses operation-details-g;
    description
      "none";
  }
  list operation-set {
    key "uuid";
    uses operation-set-g;
    description
      "none";
  }
  list outcome-element-constraints {
    key "uuid";
    uses outcome-element-constraints-g;
    description
      "none";
  }
  list processing-construct {
    key "uuid";
    uses processing-construct-g;
    description
      "none";
  }
  list physical-characteristics {
    key "uuid";
    uses physical-characteristics-g;
    description
      "none";
  }
  list physical-properties {
    key "uuid";
    uses physical-properties-g;
    description
      "none";
  }
  list pin-group {
    key "uuid";
    uses pin-group-g;
    description
      "none";
  }
  list pin-layout {
    key "uuid";
    uses pin-layout-g;
    description
      "none";
  }
  list resilient-function-block {
    key "uuid";
    uses resilient-function-block-g;
    description
      "none";
  }
  list signal-ref-pt-group {
    key "uuid";
    uses signal-ref-pt-group-g;
    description
      "none";
  }
  list spatial-properties-of-type {
    key "uuid";
    uses spatial-properties-of-type-g;
    description
      "none";
  }
  list swapability {
    key "uuid";
    uses swappability-g;
    description
      "none";
  }
  list support-constraints {
    key "uuid";
    uses support-constraints-g;
    description
      "none";
  }
  list supported-non-fru-type {
    key "uuid";
    uses supported-non-fru-type-g;
    description
      "none";
  }
  list view-mapping {
    key "uuid";
    uses view-mapping-g;
    description
      "none";
  }
  list cd-port {
    key "local-id";
    uses cd-port-g;
    description
      "none";
  }
  list clock {
    key "local-id";
    uses clock-g;
    description
      "none";
  }
  list connector {
    key "local-id";
    uses connector-g;
    description
      "none";
  }
  list control-rule {
    key "local-id";
    uses control-rule-g;
    description
      "none";
  }
  list egress-port-set {
    key "local-id";
    uses egress-port-set-g;
    description
      "none";
  }
  list fc-switch {
    key "local-id";
    uses fc-switch-g;
    description
      "none";
  }
  list fd-port {
    key "local-id";
    uses fd-port-g;
    description
      "none";
  }
  list holder {
    key "local-id";
    uses holder-g;
    description
      "none";
  }
  list ingress-port-set {
    key "local-id";
    uses ingress-port-set-g;
    description
      "none";
  }
  list layer-protocol {
    key "local-id";
    uses layer-protocol-g;
    description
      "none";
  }
  list ltp-association-rule {
    key "local-id";
    uses ltp-association-rule-g;
    description
      "none";
  }
  list multi-switched-uni-flow {
    key "local-id";
    uses multi-switched-uni-flow-g;
    description
      "none";
  }
  list port-set-spec {
    key "local-id";
    uses port-set-spec-g;
    description
      "none";
  }
  list pc-port {
    key "local-id";
    uses pc-port-g;
    description
      "none";
  }
  list pc-resilience-selector {
    key "local-id";
    uses pc-resilience-selector-g;
    description
      "none";
  }
  list configuration-and-switch-control {
    key "switch-rule";
    uses configuration-and-switch-control-g;
    description
      "none";
  }
  list equipment-structure {
    key "category";
    uses equipment-structure-g;
    description
      "none";
  }
  list equipment-instance {
    key "serial-number";
    uses equipment-instance-g;
    description
      "none";
  }
  list equipment-type {
    key "model-identifier";
    uses equipment-type-g;
    description
      "none";
  }
  list manufactured-thing {
    key "equipment-instance";
    uses manufactured-thing-g;
    description
      "none";
  }
  list manufacturer-properties {
    key "manufacturer-identifier";
    uses manufacturer-properties-g;
    description
      "none";
  }
  list network-scheme-specification {
    key "scheme-name";
    uses network-scheme-specification-g;
    description
      "none";
  }
  list operator-augmented-equipment-instance {
    key "asset-instance-identifier";
    uses operator-augmented-equipment-instance-g;
    description
      "none";
  }
  list operator-augmented-equipment-type {
    key "asset-type-identifier";
    uses operator-augmented-equipment-type-g;
    description
      "none";
  }
  list part-spec {
    key "spec-target-class";
    uses part-spec-g;
    description
      "none";
  }
  list pin {
    key "position";
    uses pin-g;
    description
      "none";
  }
  list profile-proxy {
    key "profile-proxy-mode";
    uses profile-proxy-g;
    description
      "none";
  }
  list signal-ref-pt {
    key "ltp";
    uses signal-ref-pt-g;
    description
      "none";
  }
  list specific-class-structure {
    key "class-type-name";
    uses specific-class-structure-g;
    description
      "none";
  }
}
