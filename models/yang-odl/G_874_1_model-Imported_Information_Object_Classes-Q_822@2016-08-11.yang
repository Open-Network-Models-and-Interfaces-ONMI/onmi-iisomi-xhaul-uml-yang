module G_874_1_model-Imported_Information_Object_Classes-Q_822 {
    namespace "uri:onf:G_874_1_model-Imported_Information_Object_Classes-Q_822";
    prefix G_874_1_model-Imported_Information_Object_Classes-Q_822;

    import G_874_1_model-Imported_Information_Object_Classes-X_739 {
        prefix G_874_1_model-Imported_Information_Object_Classes-X_739;
    }
    import G_874_1_model-Imported_Information_Object_Classes-X_721 {
        prefix G_874_1_model-Imported_Information_Object_Classes-X_721;
    }
    import CoreModel-CoreFoundationModule-TypeDefinitions {
        prefix CoreModel-CoreFoundationModule-TypeDefinitions;
    }
    import G_874_1_model-Type_Definitions {
        prefix G_874_1_model-Type_Definitions;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-08-11 {
        description 
            "Initial revision."; 
        reference 
            "ONF TR xyz: A YANG Data Model for Microwave Transport Networks."; 
    }

    list Q_822_CurrentData {
        key 'scannerId';
        config true;
        ordered-by system;
        uses Q_822_CurrentData;
    }
    grouping Q_822_CurrentData {
        uses G_874_1_model-Imported_Information_Object_Classes-X_739:X_739_Scanner;
        leaf suspectIntervalFlag {
            type boolean;
            description "This attribute is used to indicate that the performance data for the current period may not be reliable. Some reasons for this to occur are:- Suspect data were detected by the actual resource doing data collection.- Transition of the administrativeState attribute to/from the 'lock' state.- Transition of the operationalState to/from the 'disabled' state.- Scheduler setting that inhibits the collection function.- The performance counters were reset during the interval.- The currentData (or subclass) object instance was created during the monitoring period.";
            default false;
        }
        leaf elapsedTime {
            type int32;
        }
    }
    list Q_822_HistoryData {
        key 'historyDataId';
        config true;
        ordered-by system;
        uses Q_822_HistoryData;
    }
    grouping Q_822_HistoryData {
        uses G_874_1_model-Imported_Information_Object_Classes-X_721:X_721_Top;
        leaf historyDataId {
            type string;
        }
        leaf periodEndTime {
            type CoreModel-CoreFoundationModule-TypeDefinitions:DateAndTime;
        }
        leaf granularityPeriod {
            type G_874_1_model-Type_Definitions:GranularityPeriodType;
        }
    }
}
