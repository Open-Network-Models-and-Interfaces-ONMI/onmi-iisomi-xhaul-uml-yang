module g.874.1-model {
    namespace "urn:onf:params:xml:ns:yang:g.874.1-model";
    prefix g.874.1-model;

    import core-model {
        prefix core-model;
    }
    import ietf-yang-types {
        prefix yang;
    }

    organization "ONF (Open Networking Foundation) Open Transport Working Group - Wireless Transport Project";
    contact "WG Web: <https://www.opennetworking.org/technical-communities/areas/specification/1931-optical-transport>
             WG List:  <mailto:wireless-transport@login.opennetworking.org>
             WG Chair: Lyndon Ong
                       <mailto:lyong@ciena.com>
             WG Chair: Giorgio Cazzaniga
                       <mailto:giorgio.cazzaniga@sm-optics.com>
             Editors:  Thorsten Heinze
                       <mailto:thorsten.heinze@telefonica.com>
                       Martin Skorupski
                       <mailto:martin.skorupski@highstreet-technologies.com>";
    description "removed";
    revision 2017-03-20 {
        description "Initial version";
        reference "ONF TR 532: A YANG Data Model for Wireless Networks.";
    }
    /***********************
    * package object-classes
    **********************/ 
        grouping otn-current-data-g {
            leaf timestamp {
                type date-and-time;
                description "removed";
            }
            uses q.822-current-data-g;
            description "removed";
        }
        grouping otn-history-data-g {
            leaf suspect-interval-flag {
                type boolean;
                default false;
                description "removed";
            }
            uses q.822-history-data-g;
            description "removed";
        }

    /***********************
    * package type-definitions
    **********************/ 
        typedef directionality {
            type enumeration {
                enum sink {
                    description "none";
                }
                enum source {
                    description "none";
                }
                enum bidirectional {
                    description "none";
                }
            }
            description "removed";
        }
        typedef gcc-access {
            type enumeration {
                enum gcc1 {
                    description "none";
                }
                enum gcc2 {
                    description "none";
                }
                enum gcc1-and-gcc2 {
                    description "none";
                }
            }
            description "removed";
        }
        typedef operational-state {
            type enumeration {
                enum enabled {
                    description "none";
                }
                enum disabled {
                    description "none";
                }
            }
            description "removed";
        }
        typedef oper-type {
            type enumeration {
                enum revertive {
                    description "none";
                }
                enum non-revertive {
                    description "none";
                }
            }
            description "removed";
        }
        typedef ext-cmd-operation {
            type enumeration {
                enum exercise {
                    description "none";
                }
                enum manual-switch {
                    description "none";
                }
                enum forced-switch {
                    description "none";
                }
                enum lockout {
                    description "none";
                }
                enum release-of-manual-switch {
                    description "none";
                }
                enum release-of-forced-switch {
                    description "none";
                }
                enum release-of-lockout {
                    description "none";
                }
            }
            description "removed";
        }
        typedef administrative-state {
            type enumeration {
                enum unlocked {
                    description "none";
                }
                enum locked {
                    description "none";
                }
                enum shutting-down {
                    description "none";
                }
            }
            description "removed";
        }
        typedef oc-tk-nim-k-bit-rate {
            type enumeration {
                enum 2.5-g {
                    description "none";
                }
                enum 10-g {
                    description "none";
                }
                enum 40-g {
                    description "none";
                }
                enum 100-g {
                    description "none";
                }
            }
            description "removed";
        }
        typedef tim-det-mo {
            type enumeration {
                enum dapi {
                    description "none";
                }
                enum sapi {
                    description "none";
                }
                enum both {
                    description "none";
                }
            }
            description "removed";
        }
        typedef oc-tk-nim-problem-list {
            type enumeration {
                enum los-p {
                    description "removed";
                }
                enum oci {
                    description "removed";
                }
                enum ssf-p {
                    description "removed";
                }
                enum ssf-o {
                    description "removed";
                }
                enum ssf {
                    description "removed";
                }
                enum tim {
                    description "removed";
                }
                enum deg {
                    description "removed";
                }
                enum bdi {
                    description "removed";
                }
            }
            description "removed";
        }
        typedef tcm-monitoring {
            type enumeration {
                enum intrusive {
                    description "none";
                }
                enum non-intrusive {
                    description "none";
                }
            }
            description "removed";
        }
        typedef tcm-mode {
            type enumeration {
                enum operational {
                    description "none";
                }
                enum transparent {
                    description "none";
                }
                enum monitor {
                    description "none";
                }
            }
            description "removed";
        }
        typedef ops-mnk-ttp-k-bit-rate {
            type enumeration {
                enum 40-g {
                    description "none";
                }
                enum 100-g {
                    description "none";
                }
            }
            description "removed";
        }
        typedef ops-mnk-ttp-problem-list {
            type enumeration {
                enum los {
                    description "removed";
                }
                enum lol {
                    description "removed";
                }
            }
            description "removed";
        }
        typedef op-sn-ttp-problem-list {
            type enumeration {
                enum los {
                    description "removed";
                }
            }
            description "removed";
        }
        typedef otm-n-k-bit-rates {
            type enumeration {
                enum 2.5-g {
                    description "none";
                }
                enum 10-g {
                    description "none";
                }
                enum 40-g {
                    description "none";
                }
                enum 2.5-10-g {
                    description "none";
                }
                enum 10-40-g {
                    description "none";
                }
                enum 2.5-10-40-g {
                    description "none";
                }
            }
            description "removed";
        }
        typedef domain-interface {
            type enumeration {
                enum intra-domain {
                    description "none";
                }
                enum inter-domain {
                    description "none";
                }
            }
            description "removed";
        }
        typedef otm-n-optical-reach {
            type enumeration {
                enum intra-office {
                    description "none";
                }
                enum shorthaul {
                    description "none";
                }
                enum longhaul {
                    description "none";
                }
            }
            description "removed";
        }
        typedef apr-status {
            type enumeration {
                enum on {
                    description "none";
                }
                enum off {
                    description "none";
                }
            }
            description "removed";
        }
        typedef ot-sn-ttp-problem-list {
            type enumeration {
                enum bdi-p {
                    description "removed";
                }
                enum bdi-o {
                    description "removed";
                }
                enum bdi {
                    description "removed";
                }
                enum tim {
                    description "removed";
                }
                enum los-p {
                    description "removed";
                }
                enum los-o {
                    description "removed";
                }
                enum los {
                    description "removed";
                }
            }
            description "removed";
        }
        typedef ot-uk-ctp-adaptation {
            type enumeration {
                enum regular {
                    description "removed";
                }
                enum none {
                    description "removed";
                }
                enum vendor-specific {
                    description "removed";
                }
                enum functionally-standardized {
                    description "removed";
                }
            }
            description "removed";
        }
        typedef ot-uk-ctp-k-bit-rate {
            type enumeration {
                enum 2.5-g {
                    description "none";
                }
                enum 10-g {
                    description "none";
                }
                enum 40-g {
                    description "none";
                }
                enum 100-g {
                    description "none";
                }
            }
            description "removed";
        }
        typedef ot-uk-ctp-problem-list {
            type enumeration {
                enum lof {
                    description "removed";
                }
                enum ais {
                    description "removed";
                }
                enum lom {
                    description "removed";
                }
            }
            description "removed";
        }
        typedef ot-uk-ttp-problem-list {
            type enumeration {
                enum tim {
                    description "removed";
                }
                enum deg {
                    description "removed";
                }
                enum bdi {
                    description "removed";
                }
                enum ssf {
                    description "removed";
                }
            }
            description "removed";
        }
        typedef monitored-direction {
            type enumeration {
                enum sink {
                    description "none";
                }
                enum source {
                    description "none";
                }
            }
            description "removed";
        }
        typedef deg-thr-type {
            type enumeration {
                enum percentage {
                    description "removed";
                }
                enum number-errored-blocks {
                    description "removed";
                }
            }
            description "removed";
        }
        typedef link-type {
            type enumeration {
                enum dwdm {
                    description "none";
                }
                enum cwdm {
                    description "none";
                }
                enum no-wdm {
                    description "none";
                }
            }
            description "none";
        }
        typedef application-identifier-type {
            type enumeration {
                enum standard {
                    description "none";
                }
                enum proprietary {
                    description "none";
                }
            }
            description "none";
        }
        typedef printable-string {
            type string;
            description "none";
        }
        typedef date-and-time {
            type string;
            description "removed";
        }
        typedef aps-channel {
            type enumeration {
                enum path {
                    description "none";
                }
                enum tcm1 {
                    description "none";
                }
                enum tcm2 {
                    description "none";
                }
                enum tcm3 {
                    description "none";
                }
                enum tcm4 {
                    description "none";
                }
                enum tcm5 {
                    description "none";
                }
                enum tcm6 {
                    description "none";
                }
                enum section {
                    description "none";
                }
            }
            description "none";
        }
        typedef bit-string {
            type string;
            description "removed";
        }
        typedef delay-measurement-role {
            type enumeration {
                enum controller {
                    description "none";
                }
                enum responder {
                    description "none";
                }
            }
            description "none";
        }
        typedef resize-operation-type {
            type enumeration {
                enum increase-bw {
                    description "removed";
                }
                enum decrease-bw {
                    description "removed";
                }
            }
            description "none";
        }
        typedef granularity-period-type {
            type enumeration {
                enum unknown {
                    description "none";
                }
                enum period-15-min {
                    description "none";
                }
                enum period-24-hours {
                    description "none";
                }
            }
            description "The enumeration with the options for granularity period of the performance data.";
        }

    /***********************
    * package illustrative-object-diagrams
    **********************/ 

    /***********************
    * package imported-information-object-classes
    **********************/ 
        /***********************
        * package q.822
        **********************/ 
            grouping q.822-current-data-g {
                leaf suspect-interval-flag {
                    type boolean;
                    description "removed";
                }
                leaf elapsed-time {
                    type int64;
                    description "none";
                }
                uses x.739-scanner-g;
                description "none";
            }
            grouping q.822-history-data-g {
                leaf history-data-id {
                    type string;
                    description "none";
                }
                leaf period-end-time {
                    type yang:date-and-time;
                    description "none";
                }
                leaf granularity-period {
                    type granularity-period-type;
                    description "none";
                }
                uses x.721-top-g;
                description "none";
            }

        /***********************
        * package x.739
        **********************/ 
            grouping x.739-scanner-g {
                leaf scanner-id {
                    type string;
                    description "none";
                }
                leaf granularity-period {
                    type granularity-period-type;
                    description "none";
                }
                leaf administrative-state {
                    type core-model:administrative-state;
                    description "none";
                }
                uses x.721-top-g;
                description "none";
            }

        /***********************
        * package x.721
        **********************/ 
            grouping x.721-top-g {
                leaf object-class {
                    type object-identifier;
                    description "removed";
                }
                leaf name-binding {
                    type object-identifier;
                    description "none";
                }
                description "removed";
            }


    /***********************
    * package imported-data-types
    **********************/ 
        typedef object-instance {
            type string;
            description "none";
        }
        typedef name {
            type string;
            description "none";
        }
        typedef object-identifier {
            type string;
            description "none";
        }
        typedef generalized-time {
            type string;
            description "none";
        }
        typedef time-period {
            type string;
            description "removed";
        }

}
