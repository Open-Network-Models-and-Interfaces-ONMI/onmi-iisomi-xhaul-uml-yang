module demoapp-impl {
    yang-version 1;
    namespace "urn:opendaylight:params:xml:ns:yang:demoapp:impl";
    prefix "demoapp-impl";

    import config { prefix config; revision-date 2013-04-05; }
    import opendaylight-md-sal-binding { prefix md-sal-binding; revision-date 2013-10-28;}

    description
        "Service definition for demoapp project";

    revision "2018-12-05" {
        description
            "Initial demoapp revision";
    }

    identity demoapp {
        base config:module-type;
        config:java-name-prefix DemoAppImpl;
    }

    augment "/config:modules/config:module/config:configuration" {
        case demoapp {
            when "/config:modules/config:module/config:type = 'demoapp'";
            container broker {
                uses config:service-ref {
                    refine type {
                        mandatory true;
                        config:required-identity md-sal-binding:binding-broker-osgi-registry;
                    }
                }
            }
        }
    }


}
