module demoapp {
    yang-version 1;
    namespace "urn:opendaylight:params:xml:ns:yang:demoapp";
    prefix "demoapp";

    revision "2018-12-05" {
        description "Initial revision of Demo App model";
    }

    rpc hello-world {
        input {
            leaf name {
                type string;
            }
            leaf country {
                type string;
            }
            leaf ok {
                type string;
            }
        }
        output {
            leaf greeting {
                type string;
            }
        }
    }

    rpc hello-again {
        output {
            leaf result {
                type string;
            }
        }
    }
}
