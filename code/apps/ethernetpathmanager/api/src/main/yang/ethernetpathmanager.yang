module ethernetpathmanager {
    yang-version 1;
    namespace "urn:opendaylight:params:xml:ns:yang:ethernetpathmanager";
    prefix "ethernetpathmanager";

    revision "2018-01-19" {
        description "Initial revision of ethernetpathmanager model";
    }

    rpc hello-world {
        input {
            leaf name {
                type string;
            }
        }
        output {
            leaf greeting {
                type string;
            }
        }
    }
}
