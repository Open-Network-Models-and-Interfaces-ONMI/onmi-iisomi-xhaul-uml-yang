module websocketmanager {
    yang-version 1;
    namespace "urn:opendaylight:params:xml:ns:yang:websocketmanager";
    prefix "websocketmanager";

    revision "2015-01-05" {
        description "Initial revision of websocketmanager model";
    }

     rpc websocket-event {
        input {
            leaf nodeName {
             	type string;
            }

            leaf eventType {
             	type string;
            }

            leaf xmlEvent {
             	type string;
            }
        }
        output {
            leaf response {
                type string;
            }
        }
    }

    notification messagePushed {
      leaf message {
        type string;
      }

    }
}
