module wirelessPowerControl {
    yang-version 1;
    namespace "urn:opendaylight:params:xml:ns:yang:wirelessPowerControl";
    prefix "wirelessPowerControl";

    revision "2016-09-19" {
        description "Initial revision of wirelessPowerControl model";
    }

    rpc start {
        output {
            leaf status {
                type string;
            }
        }
    }

}
