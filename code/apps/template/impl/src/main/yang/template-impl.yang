module template-impl {
    yang-version 1;
    namespace "urn:opendaylight:params:xml:ns:yang:template:impl";
    prefix "template-impl";

    import config { prefix config; revision-date 2013-04-05; }
    import opendaylight-md-sal-binding { prefix md-sal-binding; revision-date 2013-10-28;}

    description
        "Service definition for template project";

    revision "2018-01-19" {
        description
            "Initial template revision";
    }

    identity template {
        base config:module-type;
        config:java-name-prefix TemplateImpl;
    }

    augment "/config:modules/config:module/config:configuration" {
        case template {
            when "/config:modules/config:module/config:type = 'template'";
            container broker {
                uses config:service-ref {
                    refine type {
                        mandatory true;
                        config:required-identity md-sal-binding:binding-broker-osgi-registry;
                    }
                }
            }
        }
    }


}
