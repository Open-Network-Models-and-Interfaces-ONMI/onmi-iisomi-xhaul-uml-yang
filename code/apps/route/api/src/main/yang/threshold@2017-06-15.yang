module threshold {
  namespace "urn:onf:params:xml:ns:yang:ltp-path";
  prefix threshold;

  import core-model {
    prefix core-model;
  }

  organization
   "ONF (Open Networking Foundation) Open Transport Working Group -
    Wireless Transport Project";
  contact 
    "WG Web: <https://www.opennetworking.org/technical-communities/areas/
              specification/1931-optical-transport>
     WG List:  <mailto:wireless-transport@login.opennetworking.org>
     WG Chair: Lyndon Ong
               <mailto:lyong@ciena.com>
     WG Chair: Giorgio Cazzaniga
               <mailto:giorgio.cazzaniga@sm-optics.com>
     Editor:   Liu Weihua
               <mailto:liu.wei91@zte.com.cn>";
  description 
    "This module contains a configuration of YANG definitions describing threshold of a ethernet path.";
 
  revision 2017-06-15 {
    description "Initial version";
  }

  grouping threshold_g {
        leaf max-serialization-delay {
          type uint64;
          default 1;
          description
            "unit ms";
        }
        leaf minimum-bandwidth {
          type uint64;
          default 200000;
          description
            "unit kbit/s";
        }
  }

  container threshold-of-path {
        container threshold {
            uses threshold_g;
        }
  }

}
