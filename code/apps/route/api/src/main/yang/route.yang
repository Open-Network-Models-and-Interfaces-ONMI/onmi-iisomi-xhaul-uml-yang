module route {
    yang-version 1;
    namespace "urn:opendaylight:params:xml:ns:yang:route";
    prefix "route";

    revision "2015-01-05" {
        description "Initial revision of route model";
    }

    grouping fc_desc {
        list fc {
            key 'nodeName';
            leaf nodeName {
                type string;
            }
            leaf aEnd {
                type string;
            }
            leaf zEnd {
                type string;
            }
        }
    }
    grouping status_g {
        leaf status {
            type enumeration {
                enum successful;
                enum failure;
            }
        }
    }
    rpc create {
        input {
            uses fc_desc;
            leaf vlanid {
                type int32;
            }
        }
        output {
            uses status_g;
        }
    }
    rpc delete {
        input {
            leaf vlanid {
                type int32;
            }
        }
        output {
            uses status_g;
        }
    }
    rpc create_follow_topo {
        input {
            leaf vlanid {
                type int32;
            }
        }
        output {
            uses status_g;
        }
    }
    rpc switch_follow_topo {
        input {
            leaf vlanid {
                type int32;
            }
        }
        output {
            uses status_g;
        }
    }
    rpc restore_follow_topo {
        input {
            leaf vlanid {
                type int32;
            }
        }
        output {
            uses status_g;
        }
    }
    rpc read_airInterface {
        input {
            leaf lp_id {
                type string;
            }
            leaf nodeName {
                type string;
            }
        }
    }

}
