module reRoutingFCRoute-impl-cfg {
    yang-version 1;
    namespace "urn:opendaylight:params:xml:ns:yang:reRoutingFCRoute:impl";
    prefix "rerouting-impl";

    import config { prefix config; revision-date 2013-04-05; }
    import opendaylight-md-sal-dom {prefix sal; revision-date 2013-10-28; }
    import opendaylight-md-sal-binding { prefix mdsal; revision-date 2013-10-28; }
    import opendaylight-sal-binding-broker-impl {prefix binding-impl; revision-date 2013-10-28;}

    organization "ZTE";
    contact "Weihua Liu <olinchy@icloud.com>";

    description
        "This module contains the base YANG definitions for the implementation of reRoutingFCRoute service.";

    revision "2017-05-09" {
        description
            "Initial revision";
    }

    identity re-routing-fcroute-impl {
        base config:module-type;
        config:java-name-prefix reRoutingFCRouteImpl;
    }

    augment "/config:modules/config:module/config:configuration" {
        case re-routing-fcroute-impl {
            when "/config:modules/config:module/config:type = 're-routing-fcroute-impl'";

            container broker {
                uses config:service-ref {
                    refine type {
                        mandatory true;
                        config:required-identity mdsal:binding-broker-osgi-registry;
                    }
                }
            }

            container listen-service {
                uses config:service-ref {
                    refine type {
                        mandatory true;
                        config:required-identity binding-impl:binding-new-notification-service;
                    }
                }
            }

            container rpc-registry {
                uses config:service-ref {
                    refine type {
                        mandatory true;
                        config:required-identity mdsal:binding-rpc-registry;
                    }
                }
            }
        }
    }
}
