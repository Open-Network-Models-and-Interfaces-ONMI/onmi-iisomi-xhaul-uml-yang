module reRoutingFCRoute-cfg {
    yang-version 1;
    namespace "urn:opendaylight:params:xml:ns:yang:reRoutingFCRoute:cfg";
    prefix "cfginst";

    organization "";
    contact "Weihua Liu <olinchy@icloud.com>";

    description
        "This module contains the base YANG definitions for reRoutingFCRoute service.";

    revision "2017-05-09" {
        description "Initial revision";
    }
}
