module reRoutingFCRoute {
    yang-version 1;
    namespace "urn:opendaylight:params:xml:ns:yang:reRoutingFCRoute";
    prefix "reRoutingFCRoute";

    revision "2017-05-09" {
        description "Initial revision of reRoutingFCRoute model";
    }
}
