module NetworkElement {
	yang-version 1;
    namespace "urn:opendaylight:params:xml:ns:yang:networkelement:api";
    prefix "networkelement";
	
    description
        "Network Element Model";

    revision "2016-02-03" {
        description
            "Initial revision";
    }
   	
   	grouping ne{
   		leaf name {
          	description "Network Element Name";
	        config "true";
	        type string;
        }
        
     	leaf ip {
      		description "Network Element Ip Address";
        	config "true";
        	type string;
    	}
    	
    	leaf port {
         	description "Network Element Port";
         	config "true" ;
        	type string;
         }
    	
    	leaf username {
          	description "Network Element Username";
	        config "true";
	        type string;

        }
        
        leaf password {
          	description "Network Element Password";
	        config "true";
	        type string;
        }
        
        leaf connected {
          	description "Network Element Is Connected";
	        config "true";
	        type boolean;
	        default "false";
        }
   	}
   	
    container networkElements {
    	list networkElement{
    		key "name";
    		max-elements "unbounded";
      		min-elements "0";
        	description
          		"Network Elements";
          	
          	uses ne;
    	}
    }
}
