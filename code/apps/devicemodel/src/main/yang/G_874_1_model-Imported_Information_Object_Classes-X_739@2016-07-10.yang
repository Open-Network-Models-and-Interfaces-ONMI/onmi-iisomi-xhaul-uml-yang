module G_874_1_model-Imported_Information_Object_Classes-X_739 {
    namespace "uri:onf:G_874_1_model-Imported_Information_Object_Classes-X_739";
    prefix G_874_1_model-Imported_Information_Object_Classes-X_739;

    import G_874_1_model-Imported_Information_Object_Classes-X_721 {
        prefix G_874_1_model-Imported_Information_Object_Classes-X_721;
    }
    import G_874_1_model-Type_Definitions {
        prefix G_874_1_model-Type_Definitions;
    }
    import CoreModel-CoreFoundationModule-StateModel {
        prefix CoreModel-CoreFoundationModule-StateModel;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-07-10 {
        description 
            "Initial revision."; 
        reference 
            "ONF TR xyz: A YANG Data Model for Microwave Transport Networks."; 
    }

    grouping X_739_Scanner {
        uses G_874_1_model-Imported_Information_Object_Classes-X_721:X_721_Top;
        leaf scannerId {
            type string;
        }
        leaf granularityPeriod {
            type G_874_1_model-Type_Definitions:GranularityPeriodType;
        }
        leaf administrativeState {
            type CoreModel-CoreFoundationModule-StateModel:AdministrativeState;
        }
    }
}
