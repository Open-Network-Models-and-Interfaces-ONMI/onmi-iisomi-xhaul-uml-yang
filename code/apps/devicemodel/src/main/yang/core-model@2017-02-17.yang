module core-model {
    namespace "urn:onf:params:xml:ns:yang:CoreModel";
    prefix core-model;

    organization "ONF (Open Networking Foundation) Open Transport Working Group - Wireless Transport Project";
    contact "WG Web: <https://www.opennetworking.org/technical-communities/areas/specification/1931-optical-transport>
             WG List:  <mailto:wireless-transport@login.opennetworking.org>
             WG Chair: Lyndon Ong
                       <mailto:lyong@ciena.com>
             WG Chair: Giorgio Cazzaniga
                       <mailto:giorgio.cazzaniga@sm-optics.com>
             Editors:  Thorsten Heinze
                       <mailto:thorsten.heinze@telefonica.com>
                       Martin Skorupski
                       <mailto:martin.skorupski@highstreet-technologies.com>";
    description "none";
    revision 2017-02-17 {
        description "none";
        reference "ONF TR 532: A YANG Data Model.";
    }
    /***********************
    * package core-network-model
    **********************/
        /***********************
        * package type-definitions
        **********************/
            /***********************
            * package resilience
            **********************/
                typedef protection-reason {
                    type enumeration {
                        enum wait-to-revert;
                        enum signal-degrade {
                            description "none";
                        }
                        enum signal-fail {
                            description "none";
                        }
                    }
                    description "none";
                }
                typedef route-selection-control {
                    type enumeration {
                        enum normal {
                            description "none";
                        }
                        enum manual {
                            description "none";
                        }
                        enum forced {
                            description "none";
                        }
                        enum lock-out {
                            description "none";
                        }
                    }
                    description "none";
                }
                typedef route-selection-reason {
                    type enumeration {
                        enum wait-to-revert {
                            description "none";
                        }
                        enum signal-degrade {
                            description "none";
                        }
                        enum signal-fail {
                            description "none";
                        }
                        enum normal {
                            description "none";
                        }
                        enum manual {
                            description "none";
                        }
                        enum forced {
                            description "none";
                        }
                        enum lock-out {
                            description "none";
                        }
                    }
                    description "none";
                }
                typedef switch-control {
                    type enumeration {
                        enum normal {
                            description "none";
                        }
                        enum manual {
                            description "none";
                        }
                        enum forced {
                            description "none";
                        }
                    }
                    description "none";
                }
                typedef switch-state-reason {
                    type enumeration {
                        enum wait-to-revert {
                            description "none";
                        }
                        enum signal-degrade {
                            description "none";
                        }
                        enum signal-fail {
                            description "none";
                        }
                        enum normal {
                            description "none";
                        }
                        enum manual {
                            description "none";
                        }
                        enum forced {
                            description "none";
                        }
                    }
                    description "none";
                }
                typedef reversion-mode {
                    type enumeration {
                        enum revertive {
                            description "none";
                        }
                        enum non-revertive {
                            description "none";
                        }
                    }
                    description "none";
                }
                grouping global-pac {
                    uses global-class;
                    description "none";
                }
                grouping local-pac {
                    uses local-class;
                    description "none";
                }
                typedef protection-type {
                    type string;
                    status obsolete;
                    description "none";
                }

            typedef layer-protocol-name {
                type string;
                description "none";
            }
            typedef port-role {
                type string;
                description "none";
            }
            typedef port-direction {
                type enumeration {
                    enum bidirectional {
                        description "none";
                    }
                    enum input {
                        description "none";
                    }
                    enum output {
                        description "none";
                    }
                    enum unidentified-or-unknown {
                        description "none";
                    }
                }
                description "none";
            }
            typedef forwarding-direction {
                type enumeration {
                    enum bidirectional {
                        description "none";
                    }
                    enum unidirectional {
                        description "none";
                    }
                    enum undefined-or-unknown {
                        description "none";
                    }
                }
                description "none";
            }
            typedef termination-direction {
                type enumeration {
                    enum bidirectional {
                        description "none";
                    }
                    enum sink {
                        description "none";
                    }
                    enum source {
                        description "none";
                    }
                    enum undefined-or-unknown {
                        description "none";
                    }
                }
                description "none";
            }
            typedef extended-termination-direction {
                type enumeration {
                    enum bidirectional {
                        description "none";
                    }
                    enum sink {
                        description "none";
                    }
                    enum source {
                        description "none";
                    }
                    enum undefined-or-unknown {
                        description "none";
                    }
                    enum contra-direction-sink {
                        description "none";
                    }
                    enum contra-direction-source {
                        description "none";
                    }
                }
                description "none";
            }
            typedef termination-state {
                type enumeration {
                    enum lp-can-never-terminate {
                        description "none";
                    }
                    enum lt-not-terminated {
                        description "none";
                    }
                    enum terminated-server-to-client-flow {
                        description "none";
                    }
                    enum terminated-client-to-server-flow {
                        description "none";
                    }
                    enum terminated-bidirectional {
                        description "none";
                    }
                    enum lt-permenantly-terminated {
                        description "none";
                    }
                    enum termination-state-unknown {
                        description "none";
                    }
                }
                description "none";
            }

        /***********************
        * package object-classes
        **********************/
            /***********************
            * package resilience
            **********************/
                grouping configuration-and-switch-controller {
                    leaf switch-rule {
                        type to-be-defined;
                        description "none";
                    }
                    leaf-list fc-switch {
                        type leafref {
                            path '/core-model:forwarding-construct/core-model:fc-switch/core-model:uuid';
                        }
                        description "none";
                    }
                    container control-parameters {
                        uses control-parameters-pac;
                        description "none";
                    }
                    leaf-list profile-proxy {
                        type string;
                        description "none";
                    }
                    container local-pac {
                        uses local-pac;
                        description "none";
                    }
                    container global-pac {
                        uses global-pac;
                        description "none";
                    }
                    leaf is-frozen {
                        type boolean;
                        description "none";
                    }
                    leaf is-coordinated-switching-both-ends {
                        type boolean;
                        description "none";
                    }
                    leaf-list subordinate-controller {
                        type leafref {
                            path '/core-model:network-element/core-model:ltp/core-model:lp/core-model:config-and-switch-controller/core-model:switch-rule';
                        }
                        description "none";
                    }
                    description "none";
                }
                grouping control-parameters-pac {
                    leaf reversion-mode {
                        type reversion-mode;
                        description "none";
                    }
                    leaf wait-to-revert-time {
                        type int64;
                        default 15;
                        description "none";
                    }
                    leaf prot-type {
                        type protection-type;
                        description "none";
                    }
                    leaf hold-off-time {
                        type int64;
                        description "none";
                    }
                    leaf network-scheme-specification {
                        type string;
                        description "none";
                    }
                    description "none";
                }
                grouping fc-switch {
                    leaf hold-off-time {
                        type int64;
                        description "none";
                    }
                    leaf prot-type {
                        type protection-type;
                        description "none";
                    }
                    leaf reversion-mode {
                        type reversion-mode;
                        description "none";
                    }
                    leaf-list selected-fc-port {
                        type leafref {
                            path '/core-model:forwarding-construct/core-model:fc-port/core-model:uuid';
                        }
                        description "none";
                    }
                    leaf-list profile-proxy {
                        type string;
                        description "none";
                    }
                    container internal-configuration-and-switch-control {
                        uses configuration-and-switch-controller;
                        description "none";
                    }
                    leaf switch-control {
                        type switch-control;
                        description "none";
                    }
                    leaf switch-selects-ports {
                        type port-direction;
                        description "none";
                    }
                    leaf switch-selection-reason {
                        type switch-state-reason;
                        config false;
                        description "none";
                    }
                    container control-parameters {
                        uses control-parameters-pac;
                        description "none";
                    }
                    leaf wait-to-restore-time {
                        type int64;
                        description "none";
                    }
                    uses local-class;
                    description "none";
                }

            grouping forwarding-domain {
                leaf-list layer-protocol-name {
                    type layer-protocol-name;
                    min-elements 1;
                    description "none";
                }
                leaf-list lower-level-fd {
                    type leafref {
                        path '/core-model:network-element/core-model:fd/core-model:uuid';
                    }
                    description "none";
                }
                leaf-list fc {
                    type leafref {
                        path '/core-model:forwarding-construct/core-model:uuid';
                    }
                    description "none";
                }
                leaf-list ltp {
                    type leafref {
                        path '/core-model:network-element/core-model:ltp/core-model:uuid';
                    }
                    description "none";
                }
                leaf-list lower-level-link {
                    type string;
                    description "none";
                }
                uses global-class;
                description "none";
            }
            grouping grouping-forwarding-construct {
                leaf layer-protocol-name {
                    type layer-protocol-name;
                    description "none";
                }
                leaf-list lower-level-fc {
                    type leafref {
                        path '/core-model:forwarding-construct/core-model:uuid';
                    }
                    description "none";
                }
                leaf-list fc-route {
                    type string;
                    description "none";
                }
                list fc-port {
                    key 'uuid';
                    min-elements 2;
                    uses fc-port;
                    description "none";
                }
                list fc-switch {
                    key 'uuid';
                    uses fc-switch;
                    description "none";
                }
                leaf forwarding-direction {
                    type forwarding-direction;
                    description "none";
                }
                leaf is-protection-lock-out {
                    if-feature protection-exclude-server;
                    type boolean;
                    description "none";
                }
                leaf service-priority {
                    type int64;
                    description "none";
                }
                leaf-list supported-link {
                    type string;
                    description "none";
                }
                uses global-class;
                description "none";
            }
            container network-element {
                presence  "";
                list fd {
                    key 'uuid';
                    uses forwarding-domain;
                    description "none";
                }
                list ltp {
                    key 'uuid';
                    uses logical-termination-point;
                    description "none";
                }
                uses global-class;
                description "none";
            }
            list forwarding-construct {
                key 'uuid';
                uses grouping-forwarding-construct;
                description "none";
            }
            grouping fc-port {
                leaf-list ltp {
                    type leafref {
                        path '/core-model:network-element/core-model:ltp/core-model:uuid';
                    }
                    max-elements 2;
                    description "none";
                }
                leaf role {
                    type port-role;
                    description "none";
                }
                leaf fc-port-direction {
                    type port-direction;
                    description "none";
                }
                leaf is-protection-lock-out {
                    if-feature protection-exclude-fc-port;
                    type boolean;
                    description "none";
                }
                leaf selection-priority {
                    type int64;
                    description "none";
                }
                leaf is-internal-port {
                    type boolean;
                    config false;
                    description "none";
                }
                leaf-list fc-route-feeds-fc-port-egress {
                    type string;
                    description "none";
                }
                uses local-class;
                description "none";
            }
            grouping layer-protocol {
                leaf layer-protocol-name {
                    type layer-protocol-name;
                    description "none";
                }
                leaf configured-client-capacity {
                    type to-be-defined;
                    description "none";
                }
                leaf lp-direction {
                    type termination-direction;
                    description "none";
                }
                leaf termination-state {
                    type termination-state;
                    description "none";
                }
                list config-and-switch-controller {
                    key 'switch-rule';
                    uses configuration-and-switch-controller;
                    description "none";
                }
                leaf is-protection-lock-out {
                    if-feature protection-exclude-ltp;
                    type boolean;
                    description "none";
                }
                leaf fc-blocks-signal-to-lp {
                    type string;
                    description "none";
                }
                uses local-class;
                description "none";
            }
            grouping logical-termination-point {
                leaf-list server-ltp {
                    type leafref {
                        path '/core-model:network-element/core-model:ltp/core-model:uuid';
                    }
                    description "none";
                }
                leaf-list client-ltp {
                    type leafref {
                        path '/core-model:network-element/core-model:ltp/core-model:uuid';
                    }
                    description "none";
                }
                list lp {
                    key 'uuid';
                    min-elements 1;
                    uses layer-protocol;
                    description "none";
                }
                leaf connected-ltp {
                    type leafref {
                        path '/core-model:network-element/core-model:ltp/core-model:uuid';
                    }
                    description "none";
                }
                leaf peer-ltp {
                    type leafref {
                        path '/core-model:network-element/core-model:ltp/core-model:uuid';
                    }
                    description "none";
                }
                leaf-list physical-port-reference {
                    type string;
                    description "none";
                }
                leaf-list ltp-in-other-view {
                    type leafref {
                        path '/core-model:network-element/core-model:ltp/core-model:uuid';
                    }
                    description "none";
                }
                leaf ltp-direction {
                    type termination-direction;
                    description "none";
                }
                uses global-class;
                description "none";
            }
            feature protection-exclude-server {
                description "none";
            }
            feature protection-exclude-fc-port {
                description "none";
            }
            feature protection-exclude-ltp {
                description "none";
            }

        /***********************
        * package diagrams
        **********************/

        /***********************
        * package associations
        **********************/


    /***********************
    * package core-foundation-model
    **********************/
        /***********************
        * package type-definitions
        **********************/
            typedef date-and-time {
                type string;
                description "none";
            }
            typedef bit-string {
                type string;
                description "none";
            }
            typedef real {
                type string;
                description "none";
            }
            typedef printable-string {
                type string;
                description "none";
            }
            typedef to-be-defined {
                type string;
                description "none";
            }

        /***********************
        * package super-classes-and-common-packages
        **********************/
            /***********************
            * package object-classes
            **********************/
                grouping name {
                    list name {
                        key 'value-name';
                        min-elements 1;
                        uses name-and-value;
                        description "none";
                    }
                    description "none";
                }
                grouping global-class {
                    list local-id {
                        key 'value-name';
                        uses name-and-value;
                        description "none";
                    }
                    leaf uuid {
                        type universal-id;
                        description "none";
                    }
                    uses name;
                    uses label;
                    uses extension;
                    uses state-pac;
                    description "none";
                }
                grouping local-class {
                    list local-id {
                        key 'value-name';
                        min-elements 1;
                        uses name-and-value;
                        description "none";
                    }
                    leaf uuid {
                        type universal-id;
                        description "none";
                    }
                    uses name;
                    uses label;
                    uses extension;
                    uses state-pac;
                    description "none";
                }
                grouping label {
                    list label {
                        key 'value-name';
                        uses name-and-value;
                        description "none";
                    }
                    description "none";
                }
                grouping extension {
                    list extension {
                        key 'value-name';
                        uses name-and-value;
                        description "none";
                    }
                    description "none";
                }
                grouping universal-id-authority {
                    leaf uuid {
                        type universal-id;
                        description "none";
                    }
                    description "none";
                }
                grouping name-and-value-authority {
                    leaf uuid {
                        type universal-id;
                        description "none";
                    }
                    description "none";
                }
                grouping conditional-package {
                    uses extension;
                    uses label;
                    description "none";
                }

            /***********************
            * package type-definitions
            **********************/
                grouping name-and-value {
                    leaf value-name {
                        type string;
                        description "none";
                    }
                    leaf value {
                        type string;
                        description "none";
                    }
                    description "none";
                }
                typedef universal-id {
                    type string;
                    description "none";
                }
                grouping address {
                    leaf address-name {
                        type string;
                        description "none";
                    }
                    list address-element {
                        key 'uuid';
                        uses address-element;
                        description "none";
                    }
                    description "none";
                }
                grouping local-id-and-class {
                    leaf class-of-instance {
                        type string;
                        description "none";
                    }
                    container local-id {
                        uses name-and-value;
                        description "none";
                    }
                    description "none";
                }
                grouping name-and-class {
                    leaf class-of-instance {
                        type string;
                        description "none";
                    }
                    container name {
                        uses name-and-value;
                        description "none";
                    }
                    description "none";
                }
                grouping address-element {
                    leaf address-element-name {
                        type string;
                        description "none";
                    }
                    container local-id {
                        uses local-id-and-class;
                        description "none";
                    }
                    leaf uuid {
                        type universal-id;
                        description "none";
                    }
                    container name {
                        uses name-and-class;
                        description "none";
                    }
                    leaf arbitrary-element {
                        type string;
                        description "none";
                    }
                    description "none";
                }


        /***********************
        * package state-model
        **********************/
            /***********************
            * package object-classes
            **********************/
                grouping state-pac {
                    leaf operational-state {
                        type operational-state;
                        config false;
                        description "none";
                    }
                    leaf administrative-control {
                        type administrative-control;
                        description "none";
                    }
                    leaf administrative-state {
                        type administrative-state;
                        config false;
                        description "none";
                    }
                    leaf lifecycle-state {
                        type lifecycle-state;
                        description "none";
                    }
                    description "none";
                }

            /***********************
            * package type-definitions
            **********************/
                typedef operational-state {
                    type enumeration {
                        enum disabled {
                            description "none";
                        }
                        enum enabled {
                            description "none";
                        }
                    }
                    description "none";
                }
                typedef administrative-state {
                    type enumeration {
                        enum locked {
                            description "none";
                        }
                        enum unlocked {
                            description "none";
                        }
                    }
                    description "none";
                }
                typedef administrative-control {
                    type enumeration {
                        enum unlock {
                            description "none";
                        }
                        enum lock-passive {
                            description "none";
                        }
                        enum lock-active {
                            description "none";
                        }
                        enum lock-immediate {
                            description "none";
                        }
                    }
                    description "none";
                }
                typedef extended-admin-state {
                    type enumeration {
                        enum locked {
                            description "none";
                        }
                        enum unlocked {
                            description "none";
                        }
                        enum shutting-down-active {
                            description "none";
                        }
                        enum shutting-down-passive {
                            description "none";
                        }
                    }
                    description "none";
                }
                typedef lifecycle-state {
                    type enumeration {
                        enum planned {
                            description "none";
                        }
                        enum potential {
                            description "none";
                        }
                        enum installed {
                            description "none";
                        }
                        enum pending-removal {
                            description "none";
                        }
                    }
                    description "none";
                }



    /***********************
    * package core-operations-model
    **********************/
        /***********************
        * package pattern
        **********************/
            /***********************
            * package data-types
            **********************/
                typedef action-verbs {
                    type enumeration {
                        enum create-post-add {
                            description "none";
                        }
                        enum set-update-put-modify-write-add {
                            description "none";
                        }
                        enum get-read {
                            description "none";
                        }
                        enum delete-remove {
                            description "none";
                        }
                    }
                    description "none";
                }
                typedef test-type {
                    type string;
                    description "none";
                }
                typedef activity-directive {
                    type enumeration {
                        enum structure-is-not {
                            description "none";
                        }
                        enum new-structure-and-values {
                            description "none";
                        }
                        enum incremental-structure-and-values {
                            description "none";
                        }
                        enum only-values-in-existing-structure {
                            description "none";
                        }
                        enum defined-by-verb {
                            description "none";
                        }
                    }
                    description "none";
                }

            /***********************
            * package diagrams
            **********************/
                typedef action-effort {
                    type enumeration {
                        enum best-effort {
                            description "none";
                        }
                        enum exact-match {
                            description "none";
                        }
                    }
                    description "none";
                }
                typedef pause-resume-rule {
                    type enumeration {
                        enum no-pause-possible {
                            description "none";
                        }
                    }
                    description "none";
                }

            /***********************
            * package object-classes
            **********************/
                grouping general-directives {
                    description "none";
                }
                grouping necessary-initial-condition-constraints {
                    leaf is-not {
                        type boolean;
                        description "none";
                    }
                    description "none";
                }
                grouping operation-details {
                    leaf action-verb {
                        type action-verbs;
                        description "none";
                    }
                    list necessary-initialcondition-constraints {
                        key 'is-not';
                        uses necessary-initial-condition-constraints;
                        description "none";
                    }
                    description "none";
                }
                container operation-envelope {
                    presence  "";
                    list operation-set {
                        key 'effort-and-action';
                        min-elements 1;
                        uses operation-set;
                        description "none";
                    }
                    container generaldirectives {
                        uses general-directives;
                        description "none";
                    }
                    container operationidentifiers {
                        uses operation-identifiers;
                        description "none";
                    }
                    description "none";
                }
                grouping operation-identifiers {
                    description "none";
                }
                grouping operation-set {
                    leaf effort-and-action {
                        type action-effort;
                        description "none";
                    }
                    leaf pause-resume-rule {
                        type pause-resume-rule;
                        description "none";
                    }
                    leaf is-short-lived {
                        type boolean;
                        default true;
                        description "none";
                    }
                    list operation-details {
                        key 'action-verb';
                        min-elements 1;
                        uses operation-details;
                        description "none";
                    }
                    description "none";
                }



    /***********************
    * package core-physical-model-initial
    **********************/
        /***********************
        * package rule-models
        **********************/
            /***********************
            * package connector-rules
            **********************/
                /***********************
                * package object-classes
                **********************/
                    grouping connector-in-holder {
                        leaf connector-on-equipment-for-holder {
                            type leafref {
                                path '/core-model:connector-on-equipment-for-holder/core-model:uuid';
                            }
                            description "none";
                        }
                        uses connector;
                        description "none";
                    }
                    grouping connector-cable-end {
                        leaf connector-on-equipment-for-cable {
                            type leafref {
                                path '/core-model:connector-on-equipment-for-cable/core-model:uuid';
                            }
                            description "none";
                        }
                        uses connector;
                        description "none";
                    }
                    grouping connector-on-equipment-for-cable {
                        leaf connector-cable-end {
                            type leafref {
                                path '/core-model:connector-cable-end/core-model:uuid';
                            }
                            description "none";
                        }
                        uses connector;
                        description "none";
                    }
                    grouping connector-on-equipment-for-holder {
                        leaf connector-in-holder {
                            type leafref {
                                path '/core-model:connector-in-holder/core-model:uuid';
                            }
                            description "none";
                        }
                        uses connector;
                        description "none";
                    }



        /***********************
        * package equipment-detail
        **********************/
            /***********************
            * package object-classes
            **********************/
                /***********************
                * package dynamic-details
                **********************/
                    grouping function-enablers {
                        leaf power-state {
                            type to-be-defined;
                            description "none";
                        }
                        description "none";
                    }
                    grouping mechanical-functions {
                        leaf rotation-speed {
                            type to-be-defined;
                            description "none";
                        }
                        description "none";
                    }
                    grouping physical-properties {
                        leaf temperature {
                            type to-be-defined;
                            description "none";
                        }
                        description "none";
                    }
                    grouping holder-monitors {
                        leaf is-active {
                            type boolean;
                            description "none";
                        }
                        leaf is-actual-mismatch-with-expected {
                            type boolean;
                            description "none";
                        }
                        leaf aggregate-function {
                            type string;
                            description "none";
                        }
                        description "none";
                    }
                    grouping location {
                        container equipment-location {
                            uses address;
                            description "none";
                        }
                        container geographical-location {
                            uses address;
                            description "none";
                        }
                        description "none";
                    }

                /***********************
                * package invariant-details
                **********************/
                    grouping category {
                        leaf category {
                            type equipment-category;
                            description "none";
                        }
                        description "none";
                    }
                    grouping equipment-instance {
                        leaf manufacture-date {
                            type string;
                            description "none";
                        }
                        leaf serial-number {
                            type string;
                            description "none";
                        }
                        leaf asset-instance-identifier {
                            type string;
                            description "none";
                        }
                        description "none";
                    }
                    grouping equipment-type {
                        leaf description {
                            type string;
                            description "none";
                        }
                        leaf model-identifier {
                            type string;
                            description "none";
                        }
                        leaf part-type-identifier {
                            type string;
                            description "none";
                        }
                        leaf type-name {
                            type string;
                            description "none";
                        }
                        leaf version {
                            type string;
                            description "none";
                        }
                        description "none";
                    }
                    grouping holder-structure {
                        leaf holder-category {
                            type holder-category;
                            description "none";
                        }
                        leaf is-captive {
                            type boolean;
                            description "none";
                        }
                        leaf is-guided {
                            type boolean;
                            description "none";
                        }
                        leaf is-quantized-space {
                            type boolean;
                            description "none";
                        }
                        description "none";
                    }
                    grouping manufactured-thing {
                        container manufacturer-properties {
                            uses manufacturer-properties;
                            description "none";
                        }
                        container equipment-type {
                            uses equipment-type;
                            description "none";
                        }
                        container equipment-instance {
                            uses equipment-instance;
                            description "none";
                        }
                        container operator-augmented-equipment-type {
                            uses operator-augmented-equipment-type;
                            description "none";
                        }
                        description "none";
                    }
                    grouping manufacturer-properties {
                        leaf manufacturer-identifier {
                            type string;
                            description "none";
                        }
                        leaf manufacturer-name {
                            type string;
                            description "none";
                        }
                        description "none";
                    }
                    grouping mechanical-features {
                        description "none";
                    }
                    grouping operator-augmented-equipment-type {
                        leaf asset-type-identifier {
                            type string;
                            description "none";
                        }
                        description "none";
                    }
                    grouping physical-characteristics {
                        leaf weight-characteristics {
                            type to-be-defined;
                            description "none";
                        }
                        leaf fire-characteristics {
                            type to-be-defined;
                            description "none";
                        }
                        leaf materials {
                            type to-be-defined;
                            description "none";
                        }
                        description "none";
                    }
                    grouping physical-rating {
                        leaf thermal-rating {
                            type to-be-defined;
                            description "none";
                        }
                        leaf power-rating {
                            type to-be-defined;
                            description "none";
                        }
                        description "none";
                    }
                    grouping position {
                        leaf relative-position {
                            type to-be-defined;
                            description "none";
                        }
                        description "none";
                    }
                    grouping spatial-properties-of-type {
                        leaf height {
                            type to-be-defined;
                            description "none";
                        }
                        leaf width {
                            type to-be-defined;
                            description "none";
                        }
                        leaf length {
                            type to-be-defined;
                            description "none";
                        }
                        description "none";
                    }
                    grouping swapability {
                        leaf is-hot-swappable {
                            type boolean;
                            default true;
                            description "none";
                        }
                        description "none";
                    }



        /***********************
        * package equipment-pattern-structure
        **********************/
            /***********************
            * package object-classes
            **********************/
                grouping cable {
                    list connector {
                        key 'uuid';
                        min-elements 1;
                        uses connector;
                        description "none";
                    }
                    container manufactured-thing {
                        uses manufactured-thing;
                        description "none";
                    }
                    container physical-characteristics {
                        uses physical-characteristics;
                        description "none";
                    }
                    container mechanical-features {
                        uses mechanical-features;
                        description "none";
                    }
                    container spatial-properties-of-type {
                        uses spatial-properties-of-type;
                        description "none";
                    }
                    uses global-class;
                    description "none";
                }
                grouping connector {
                    leaf connector {
                        type string;
                        description "none";
                    }
                    list pin {
                        key 'position';
                        min-elements 1;
                        uses pin;
                        description "none";
                    }
                    leaf orientation {
                        type connector-and-pin-orientation;
                        description "none";
                    }
                    container manufactured-thing {
                        uses manufactured-thing;
                        description "none";
                    }
                    container position {
                        uses position;
                        description "none";
                    }
                    container mechanical-features {
                        uses mechanical-features;
                        description "none";
                    }
                    container pin-layout {
                        uses pin-layout;
                        description "none";
                    }
                    leaf connector-type {
                        type to-be-defined;
                        description "none";
                    }
                    uses local-class;
                    uses group-of-pins;
                    description "none";
                }
                grouping grouping-equipment {
                    list connector {
                        key 'uuid';
                        uses connector;
                        description "none";
                    }
                    list contained-holder {
                        key 'uuid';
                        uses holder;
                        description "none";
                    }
                    list exposed-cable {
                        key 'uuid';
                        uses cable;
                        description "none";
                    }
                    container manufactured-thing {
                        uses manufactured-thing;
                        description "none";
                    }
                    container spatial-properties-of-type {
                        uses spatial-properties-of-type;
                        description "none";
                    }
                    container mechanical-features {
                        uses mechanical-features;
                        description "none";
                    }
                    container physical-properties {
                        uses physical-properties;
                        description "none";
                    }
                    container function-enablers {
                        uses function-enablers;
                        description "none";
                    }
                    container mechanical-functions {
                        uses mechanical-functions;
                        description "none";
                    }
                    container physical-characteristics {
                        uses physical-characteristics;
                        description "none";
                    }
                    container swapability {
                        uses swapability;
                        description "none";
                    }
                    container category {
                        uses category;
                        description "none";
                    }
                    container physical-rating {
                        uses physical-rating;
                        description "none";
                    }
                    leaf is-field-replaceable {
                        type boolean;
                        default true;
                        config false;
                        description "none";
                    }
                    leaf-list function-block {
                        type string;
                        description "none";
                    }
                    container expected-equipment {
                        uses expected-equipment;
                        description "none";
                    }
                    container actual-equipment {
                        uses actual-equipment;
                        description "none";
                    }
                    container location {
                        uses location;
                        description "none";
                    }
                    uses global-class;
                    description "none";
                }
                list equipment {
                    key 'uuid';
                    uses grouping-equipment;
                    description "none";
                 }
                grouping holder {
                    leaf-list connector {
                        type leafref {
                            path '/core-model:equipment/core-model:exposed-cable/core-model:connector/core-model:uuid';
                        }
                        description "none";
                    }
                    leaf occupying-fru {
                        type leafref {
                            path '/core-model:equipment/core-model:uuid';
                        }
                        description "none";
                    }
                    container spatial-properties-of-type {
                        uses spatial-properties-of-type;
                        description "none";
                    }
                    container holder-monitors {
                        uses holder-monitors;
                        description "none";
                    }
                    container holder-location {
                        uses address;
                        description "none";
                    }
                    container position {
                        uses position;
                        description "none";
                    }
                    container holder-structure {
                        uses holder-structure;
                        description "none";
                    }
                    container physical-rating {
                        uses physical-rating;
                        description "none";
                    }
                    leaf-list supported-equipment {
                        type string;
                        min-elements 1;
                        description "none";
                    }
                    container expected-holder {
                        uses expected-holder;
                        description "none";
                    }
                    container actual-holder {
                        uses actual-holder;
                        description "none";
                    }
                    uses local-class;
                    description "none";
                }

            /***********************
            * package data-types
            **********************/
                typedef connector-and-pin-orientation {
                    type enumeration {
                        enum male {
                            description "none";
                        }
                        enum female {
                            description "none";
                        }
                        enum symmetric-neutral {
                            description "none";
                        }
                    }
                    description "none";
                }
                typedef equipment-category {
                    type enumeration {
                        enum subrack {
                            description "none";
                        }
                        enum circuit-pack {
                            description "none";
                        }
                        enum small-formfactor-pluggable {
                            description "none";
                        }
                        enum stand-alone-unit {
                            description "none";
                        }
                        enum rack {
                            description "none";
                        }
                    }
                    description "none";
                }
                typedef holder-category {
                    type enumeration {
                        enum slot {
                            description "none";
                        }
                    }
                    description "none";
                }


        /***********************
        * package expected-and-actual
        **********************/
            /***********************
            * package object-classes
            **********************/
                grouping actual-holder {
                    description "none";
                }
                grouping expected-holder {
                    description "none";
                }
                grouping actual-equipment {
                    description "none";
                }
                grouping expected-equipment {
                    description "none";
                }


        /***********************
        * package connector-and-pin
        **********************/
            /***********************
            * package object-classes
            **********************/
                grouping pin {
                    leaf position {
                        type leafref {
                            path '/core-model:equipment/core-model:exposed-cable/core-model:connector/core-model:position/core-model:relative-position';
                        }
                        description "none";
                    }
                    leaf orientation {
                        type connector-and-pin-orientation;
                        description "none";
                    }
                    description "none";
                }
                grouping pin-group {
                    leaf-list pin {
                        type leafref {
                            path '/core-model:equipment/core-model:exposed-cable/core-model:connector/core-model:pin/core-model:position';
                        }
                        min-elements 1;
                        description "none";
                    }
                    uses port;
                    uses group-of-pins;
                    description "none";
                }
                grouping pin-layout {
                    list position {
                        key 'relative-position';
                        min-elements 1;
                        uses position;
                        description "none";
                    }
                    description "none";
                }
                grouping port {
                    description "none";
                }
                grouping signal-ref-pt {
                    leaf ltp {
                        type leafref {
                            path '/core-model:network-element/core-model:ltp/core-model:uuid';
                        }
                        description "none";
                    }
                   description "none";
                }
                grouping signal-ref-pt-group {
                    leaf pin-group {
                        type leafref {
                            path '/core-model:pin-group/core-model:pin';
                        }
                        description "none";
                    }
                    leaf-list signal-ref-pt {
                        type leafref {
                            path '/core-model:signal-ref-pt/core-model:ltp';
                        }
                        min-elements 1;
                        description "none";
                    }
                    uses port;
                    description "none";
                }
                grouping elemental-signals {
                    leaf-list pin {
                        type leafref {
                            path '/core-model:equipment/core-model:exposed-cable/core-model:connector/core-model:pin/core-model:position';
                        }
                        min-elements 1;
                        description "none";
                    }
                    description "none";
                }
                grouping group-of-pins {
                    description "none";
                }



}
