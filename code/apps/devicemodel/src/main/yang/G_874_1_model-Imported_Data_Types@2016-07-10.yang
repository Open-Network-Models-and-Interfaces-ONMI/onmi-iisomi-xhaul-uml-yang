module G_874_1_model-Imported_Data_Types {
    namespace "uri:onf:G_874_1_model-Imported_Data_Types";
    prefix G_874_1_model-Imported_Data_Types;


    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        '<p>Version 2.02; outcome of the 10/2013 Nuremberg meeting.<br>Version 2.03; updates for Geneva 03-2014<br>Version 2.04; updates for Shanghai 09-2014<br>Version 2.05; input to Geneva 11-2014<br>Version 2.06; output from Geneva 11-2014<br>Version 2.07; using OpenProfile 3-2015<br>Version 2.08; output from Geneva 06-2015</p>';

    revision 2016-07-10 {
        description 
            "Initial revision."; 
        reference 
            "ONF TR xyz: A YANG Data Model for Microwave Transport Networks."; 
    }

    typedef ObjectInstance {
        type string;
    }
    typedef Name {
        type string;
    }
    typedef ObjectIdentifier {
        type string;
    }
    typedef GeneralizedTime {
        type string;
    }
    typedef TimePeriod {
        description "This primitive Type is imported from X.739.";
        type string;
    }
}
