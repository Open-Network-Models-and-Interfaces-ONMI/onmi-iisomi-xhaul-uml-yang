module MicrowaveModel-NetworkElement-CurrentProblemList {
    namespace "uri:onf:MicrowaveModel-NetworkElement-CurrentProblemList";
    prefix MicrowaveModel-NetworkElement-CurrentProblemList;

    import MicrowaveModel-ObjectClasses-SuperClasses {
        prefix MicrowaveModel-ObjectClasses-SuperClasses;
    }
    import MicrowaveModel-TypeDefinitions {
        prefix MicrowaveModel-TypeDefinitions;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module is an add-on to the ONF TR532 supporting alarms for object classes not
         moduled by ONF TR532.';

    revision 2016-11-20 {
        description 
            "Initial revision."; 
        reference 
            "ONF TR 532: A YANG Data Model for Microwave Transport Networks."; 
    }

    feature all-network-element-alarms {
        description "Feature 'all-network-element' is optional to support alarms of object classes not modeled by ONF TR 532.";
    }
    
    grouping genericCurrentProblemType {
        uses MicrowaveModel-ObjectClasses-SuperClasses:MwCurrentProblem;
        leaf objectIdRef {
            type string;
            description "A string representation of alarmed object.";
        }
        leaf problemName {
            type string;
            config false;
            description "Name of the alarm.";
            default "";
        }
        leaf problemSeverity {
            type MicrowaveModel-TypeDefinitions:severityType;
            description "Severity of the alarm.";
            default "warning";
        }
    }

    container NetworkElementCurrentProblems {
        config false;
        if-feature all-network-element-alarms;
        list currentProblemList {
            key 'sequenceNumber';
            ordered-by system;
            uses genericCurrentProblemType;
        }
    }
    
}
