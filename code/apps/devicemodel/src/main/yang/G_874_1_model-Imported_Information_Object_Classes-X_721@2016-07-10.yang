module G_874_1_model-Imported_Information_Object_Classes-X_721 {
    namespace "uri:onf:G_874_1_model-Imported_Information_Object_Classes-X_721";
    prefix G_874_1_model-Imported_Information_Object_Classes-X_721;

    import G_874_1_model-Imported_Data_Types {
        prefix G_874_1_model-Imported_Data_Types;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-07-10 {
        description 
            "Initial revision."; 
        reference 
            "ONF TR xyz: A YANG Data Model for Microwave Transport Networks."; 
    }

    grouping X_721_Top {
        description "This is the top level of managed object class hierarchy and every other managed object class is a specialization of either this generic class (top) or a specialization of subclass of top. The parameter miscellaneousError is to be used when a processing failure has occurred and the error condition encountered does not match any of object's defined specific error types.";
        leaf objectClass {
            type G_874_1_model-Imported_Data_Types:ObjectIdentifier;
            description "ObjectClass ::= CHOICE{    globalForm    [0] OBJECT IDENTIFIER,
                localForm    [1] INTEGER}";
        }
        leaf nameBinding {
            type G_874_1_model-Imported_Data_Types:ObjectIdentifier;
        }
    }
}
