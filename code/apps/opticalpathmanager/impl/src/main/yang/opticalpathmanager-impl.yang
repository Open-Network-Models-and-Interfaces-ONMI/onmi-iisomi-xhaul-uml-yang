module opticalpathmanager-impl {
    yang-version 1;
    namespace "urn:opendaylight:params:xml:ns:yang:opticalpathmanager:impl";
    prefix "opticalpathmanager-impl";

    import config { prefix config; revision-date 2013-04-05; }
    import opendaylight-md-sal-binding { prefix md-sal-binding; revision-date 2013-10-28;}

    description
        "Service definition for opticalpathmanager project";

    revision "2018-01-19" {
        description
            "Initial opticalpathmanager revision";
    }

    identity opticalpathmanager {
        base config:module-type;
        config:java-name-prefix OpticalPathManagerImpl;
    }

    augment "/config:modules/config:module/config:configuration" {
        case opticalpathmanager {
            when "/config:modules/config:module/config:type = 'opticalpathmanager'";
            container broker {
                uses config:service-ref {
                    refine type {
                        mandatory true;
                        config:required-identity md-sal-binding:binding-broker-osgi-registry;
                    }
                }
            }
        }
    }


}
