module genericpathmanager-impl {
    yang-version 1;
    namespace "urn:opendaylight:params:xml:ns:yang:genericpathmanager:impl";
    prefix "genericpathmanager-impl";

    import config { prefix config; revision-date 2013-04-05; }
    import opendaylight-md-sal-binding { prefix md-sal-binding; revision-date 2013-10-28;}

    description
        "Service definition for genericpathmanager project";

    revision "2018-01-19" {
        description
            "Initial genericpathmanager revision";
    }

    identity genericpathmanager {
        base config:module-type;
        config:java-name-prefix GenericPathManagerImpl;
    }

    augment "/config:modules/config:module/config:configuration" {
        case genericpathmanager {
            when "/config:modules/config:module/config:type = 'genericpathmanager'";
            container broker {
                uses config:service-ref {
                    refine type {
                        mandatory true;
                        config:required-identity md-sal-binding:binding-broker-osgi-registry;
                    }
                }
            }
        }
    }


}
