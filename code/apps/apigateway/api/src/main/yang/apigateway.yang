module apigateway {
    yang-version 1;
    namespace "urn:opendaylight:params:xml:ns:yang:apigateway";
    prefix "apigateway";

    revision "2017-10-16" {
        description "Initial revision of apigateway model";
    }
    
    rpc get {
        input {
            leaf name {
                type string;
            }
        }
        output {
            leaf greeting {
                type string;
            }
        }
    }
    
}
