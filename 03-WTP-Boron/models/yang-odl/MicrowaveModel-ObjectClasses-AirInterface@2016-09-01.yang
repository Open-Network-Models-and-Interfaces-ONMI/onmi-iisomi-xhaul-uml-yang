module MicrowaveModel-ObjectClasses-AirInterface {
    namespace "uri:onf:MicrowaveModel-ObjectClasses-AirInterface";
    prefix MicrowaveModel-ObjectClasses-AirInterface;

    import CoreModel-CoreNetworkModule-ObjectClasses {
        prefix CoreModel-CoreNetworkModule-ObjectClasses;
    }
    import MicrowaveModel-TypeDefinitions {
        prefix MicrowaveModel-TypeDefinitions;
    }
    import CoreModel-CoreFoundationModule-TypeDefinitions {
        prefix CoreModel-CoreFoundationModule-TypeDefinitions;
    }
    import CoreModel-CoreFoundationModule-SuperClassesAndCommonPackages {
        prefix CoreModel-CoreFoundationModule-SuperClassesAndCommonPackages;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-09-01 {
        description 
            "Initial revision."; 
        reference 
            "ONF TR xyz: A YANG Data Model for Microwave Transport Networks."; 
    }

    list MW_AirInterface_Pac {
        description "LTP(MWPS-TTP)";
        key 'layerProtocol';
        config true;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container airInterfaceCapability {
            config false;
            uses AirInterfaceCapability;
        }
        container airInterfaceConfiguration {
            config true;
            uses AirInterfaceConfiguration;
        }
        container airInterfaceStatus {
            config false;
            uses AirInterfaceStatus;
        }
        container airInterfaceCurrentProblems {
            config false;
            uses AirInterfaceCurrentProblems;
        }
        container airInterfaceCurrentPerformance {
            config false;
            uses AirInterfaceCurrentPerformance;
        }
        container airInterfaceHistoricalPerformances {
            config false;
            uses AirInterfaceHistoricalPerformances;
        }
    }
    grouping AirInterfaceCapability {
        description "Describes the 'analog' capabilities of modem and transmitter of the microwave device. Value ranges of attributes are not independently (e.g. min. and max. transmit power depends on modulation). Legal combinations of values are expressed in transmissionModeTypes.";
        leaf typeOfEquipment {
            type string;
            config false;
            description "This parameter indicates the equipment type. Instead of uploading the complete set of capabilities, capabilities of the same equipment type could be reused. Should be unique for a combination of modem, radio and their respective firmware.";
            default "Type of equipment not yet defined.";
        }
        leaf txFrequencyMin {
            type int32;
            config false;
            description "Value of the minimum transmit frequency tunable at the air interface.";
            units "kHz";
            default -1;
        }
        leaf txFrequencyMax {
            type int32;
            config false;
            description "Value of the maximum transmit frequency tunable at the air interface.";
            units "kHz";
            default -1;
        }
        leaf rxFrequencyMin {
            type int32;
            config false;
            description "Value of the minimum receive frequency tunable at the air interface.";
            units "kHz";
            default -1;
        }
        leaf rxFrequencyMax {
            type int32;
            config false;
            description "Value of the maximum receive frequency tunable at the air interface.";
            units "kHz";
            default -1;
        }
        leaf adaptiveModulationIsAvail {
            type boolean;
            config false;
            description "In case the device is capable of adaptive modulation, this field shall contain a 'true'.";
            default false;
        }
        leaf mimoIsAvail {
            type boolean;
            config false;
            description "In case the device is capable of MIMO, this field shall contain a 'true'.";
            default false;
        }
        leaf mimoChannels {
            type int8;
            config false;
            description "Maximum number (n) of spatial multiplexing streams that can be conveyed by an n x n MIMO configuration.";
            units "channels";
            default 1;
        }
        leaf alicIsAvail {
            type boolean;
            config false;
            description "In case the microwave radio is capable of Adjacent Link Interference Cancelation (canceling of interference cause by transmitters located at the same site), this field shall contain a 'true'.";
            default false;
        }
        leaf atpcIsAvail {
            type boolean;
            config false;
            description "In case the microwave radio is capable of ATPC, this field shall contain a 'true'.";
            default false;
        }
        leaf atpcRange {
            type int8;
            config false;
            description "Extent of the ATPC range.";
            units "dB";
            default 0;
        }
        leaf encryptionIsAvail {
            type boolean;
            config false;
            description "Shall be marked 'true', if payload encryption is available.";
            default false;
        }
        leaf loopBackIsAvail {
            type boolean;
            config false;
            description "In case the radio is capable of looping back header information of the air interface, this field shall contain a 'true'.";
            default false;
        }
        leaf maintenanceTimerRange {
            type string;
            config false;
            description "Available time periods for maintenance configurations (e.g. the loop back of microwave header information) to be described. Concrete values shall be separated by commas (e.g. '10, 60, 360'). Ranges shall be expressed as two values separated by a minus (e.g. '10-360').";
            units "s";
            default "Range of the maintenance timer not yet defined.";
        }
        leaf supportedAlarms {
            type string;
            config false;
            description "Available alarms to be listed. Mandatory:'signalIsLost','rslIsExceeded','temperatureIsExceeded','modemIsFaulty','radioIsFaulty' and 'modulationIsDownShifted'. Further alarms might be added by the device. Names are to be separated by commas.";
            default "Supported alarms not yet defined.";
        }
        list supportedChannelPlanList {
            description "List of channel spacing that are supported by the device.";
            key 'supportedChannelPlan';
            ordered-by system;
            uses MicrowaveModel-TypeDefinitions:channelPlanType;
            min-elements 1;
        }
    }
    grouping AirInterfaceConfiguration {
        description "Configuration of the radio link.";
        leaf airInterfaceName {
            type string;
            description "Operator specific microwave link ID (often used for coding area, type of element and sequential number).";
            default "Air interface ID not yet defined.";
        }
        leaf radioSignalID {
            type string;
            description "The radioSignalId is transmitted on the air interface so the remote site of the link synchronizes on the correct transmitter. The local radio MUST NOT synchronize on a radio signal with a different radioSignalId. The link ID is neither an ID necessary to span the model nor an ID referencing external data. It is just some sort of name of the link transmitted so the correct remote site can be identified in an interference situation.
                The value zero might be used to make the microwave to disable the link ID check.";
            default "Radio signal ID not yet defined.";
        }
        leaf txFrequency {
            type int32;
            description "Center frequency of the transmit channel. The values to be configured have to exactly match the values listed in the international agreement referenced in channelPlanID. In case of automated selection of the transmit frequency this field shall describe the lowest center frequency selectable.";
            units "kHz";
            default -1;
        }
        leaf rxFrequency {
            type int32;
            description "Center frequency of the receive channel.";
            units "kHz";
            default -1;
        }
        leaf txChannelBandwidth {
            type int32;
            description "Bandwidth of the transmit channel. The value shall be expressed explicitly (means in kHz) not as a reference to an international agreement. The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;";
            units "kHz";
            default -1;
        }
        leaf rxChannelBandwidth {
            type int32;
            description "Bandwidth of the receive channel. The value shall be expressed explicitly (means in kHz) not as a reference to an international agreement. The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;";
            units "kHz";
            default -1;
        }
        leaf polarization {
            type MicrowaveModel-TypeDefinitions:polarizationType;
            description "Allows documenting the polarization of the air interface.";
            default "not-specified";
        }
        leaf powerIsOn {
            type boolean;
            description "Power ON. Activation of the entire radio in a split mount configuration shall be expressed as a 'true'.";
            default true;
        }
        leaf transmitterIsOn {
            type boolean;
            description "Activation of the transmitter inside the radio shall be expressed as a 'true'.";
            default false;
        }
        leaf receiverIsOn {
            type boolean;
            description "Activation of the receiver inside the radio shall be expressed as a 'true'. Attribute shall also be used for RX main and RX diversity squelches in case of diversity configurations.
                Maintenance Feature";
            default true;
        }
        leaf txPower {
            type int8;
            description "Transmit power to be configured on the microwave link. Signed Byte is required. The actually operated transmit power might be lower depending on adaptive modulation and ATPC.";
            units "dBm";
            default 99;
        }
        leaf adaptiveModulationIsOn {
            type boolean;
            description "Adaptive Modulation. Activation of adaptive modulation shall be expressed as a 'true'.";
            default false;
        }
        leaf modulationMin {
            type int16;
            description "Minimum modulation to be configured (in case adaptive modulation is not used, this value represents also the fixed modulation). The modulation scheme shall be described by the number of symbols (e.g. BPSK->'2' or 256QAM->'256'). Allowed values are defined in TypeDefinitions::transmissionModeType::modulationScheme.";
            units "symbols";
            default -1;
        }
        leaf modulationMax {
            type int16;
            description "Maximum modulation to be configured. The value of this field is only relevant, if Adaptive Modulation has been activated. The modulation scheme shall be described by the number of symbols (e.g. BPSK->'2' or 256QAM->'256'). Allowed values are defined in TypeDefinitions::transmissionModeType::modulationScheme.";
            units "symbols";
            default -1;
        }
        leaf xpicIsOn {
            type boolean;
            description "Activation of Cross Polarization Interference Cancelation shall be expressed as a 'true'. In case XPIC is not available for the current combination of channel bandwidth and modulation or the hardware in general, this parameter shall always be set to 'false'.";
            default false;
        }
        leaf mimoIsOn {
            type boolean;
            description "Activation of Multiple Input Multiple Output (MIMO) shall be expressed as a 'true'.";
            default false;
        }
        leaf alicIsOn {
            type boolean;
            description "Activation of Adjacent Link Interference Cancelation (ALIC) shall be expressed as a 'true'.";
            default false;
        }
        leaf atpcIsOn {
            type boolean;
            description "ATPC. Activation of Automated Transmit Power Control shall be expressed as a 'true'.";
            default false;
        }
        leaf atpcThreshUpper {
            type int16;
            description "If the receive level is higher than the upper threshold value, the transmitter is notified to decrease transmit power.";
            units "dBm";
            default 99;
        }
        leaf atpcThreshLower {
            type int16;
            description "If the receive level is lower than the lower threshold value, the transmitter is notified to increase transmit power.";
            units "dBm";
            default 99;
        }
        leaf autoFreqSelectIsOn {
            type boolean;
            description "Activation of automatically selecting the transmit frequency in unlicensed bands shall be expressed as a 'true'.";
            default false;
        }
        leaf autoFreqSelectRange {
            type int8;
            description "Number of transmit channels (starting at the center frequency defined in txFrequency and with channel bandwidth according to txChannelBandwidth) that define the range within the transmit frequency can automatically been chosen. ";
            units "channels";
            default -1;
        }
        leaf modulationIsOn {
            type boolean;
            description "De-activation of the modulation of the carrier signal for fault management shall be expressed as a 'false'.
                Maintenance Feature";
            default true;
        }
        leaf encryptionIsOn {
            type boolean;
            description "Activates encryption of the payload.";
            default false;
        }
        leaf cryptographicKey {
            type string;
            description "Key for transforming plaintext into ciphertext data.";
            default "Cryptographic key not yet defined.";
        }
        leaf loopBackIsOn {
            type boolean;
            description "If this attribute is set to 'true', the received IF signal is transmitted back to the remote end.
                Maintenance Feature";
            default false;
        }
        leaf maintenanceTimer {
            type int32;
            description "Time of existence of any maintenance configuration (e.g. the loop back of microwave header information). Valid values are defined in AirInterface::AirInterfaceCapability::maintenanceTimerRange.";
            units "s";
            default -1;
        }
        list problemKindSeverityList {
            description "Severity of the problem to be configured.";
            key 'problemKindName';
            config true;
            ordered-by system;
            uses MicrowaveModel-TypeDefinitions:airInterfaceProblemSeverityType;
            min-elements 6;
        }
    }
    grouping AirInterfaceStatus {
        description "Measurements of current values on the air interface and operational status of the device.";
        leaf txFrequencyCur {
            type int32;
            config false;
            description "Center frequency of the currently operated transmit channel.";
            units "kHz";
            default -1;
        }
        leaf rxFrequencyCur {
            type int32;
            config false;
            description "Center frequency of the currently operated receive channel.";
            units "kHz";
            default -1;
        }
        leaf txLevelCur {
            type int8;
            config false;
            description "Current transmit level.";
            units "dBm";
            default 99;
        }
        leaf rxLevelCur {
            type int8;
            config false;
            description "Current receive level.";
            units "dBm";
            default 99;
        }
        leaf modulationCur {
            type int16;
            config false;
            description "Currently operated modulation on transmit path. The modulation scheme shall be described by the number of symbols (e.g. BPSK->'2' or 256QAM->'256'). Allowed values are defined in TypeDefinitions::transmissionModeType::modulationScheme.";
            units "symbols";
            default -1;
        }
        leaf informationRateCur {
            type int8;
            config false;
            description "Information rate of the currently operated coding scheme.";
            units "%";
            default -1;
        }
        leaf snirCur {
            type int8;
            config false;
            description "Currently measured signal to (noise+interference) ratio.";
            units "dB";
            default -99;
        }
        leaf xpdCur {
            type int8;
            config false;
            description "Currently measured cross polarization discrimination.";
            units "dB";
            default -99;
        }
        leaf rfTempCur {
            type int8;
            config false;
            description "Current temperature (in degree Celsius) of the radio module inside the outdoor unit.";
            units "Celsius";
            default -99;
        }
        leaf lastStatusChange {
            type CoreModel-CoreFoundationModule-TypeDefinitions:DateAndTime;
            config false;
            description "Time the Air Interface entered its current operational status. 
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
            default "20101120140000.0Z+1";
        }
        leaf radioPowerIsUp {
            type boolean;
            config false;
            description "If the radio unit has power and is switched on, this shall be expressed as a 'true'.";
            default false;
        }
        leaf linkIsUp {
            type boolean;
            config false;
            description "If connection is established to the remote site with the same linkID, this shall be expressed as a 'true'.";
            default false;
        }
        leaf xpicIsUp {
            type boolean;
            config false;
            description "If XPIC is currently actually working (not just configured), this shall be expressed as a 'true'.";
            default false;
        }
        leaf mimoIsUp {
            type boolean;
            config false;
            description "If MIMO is currently actually working (not just configured), this shall be expressed as a 'true'.";
            default false;
        }
        leaf alicIsUp {
            type boolean;
            config false;
            description "If Adjacent Link Interference Cancelation (ALIC) is currently actually working (not just configured), this shall be expressed as a 'true'.";
            default false;
        }
        leaf atpcIsUp {
            type boolean;
            config false;
            description "If ATPC is currently actually working (not just configured), this shall be expressed as a 'true'.";
            default false;
        }
        leaf autoFreqSelectIsUp {
            type boolean;
            config false;
            description "If automated frequency selection is currently actually working (not just configured), this shall be expressed as a 'true'.";
            default false;
        }
        leaf loopBackIsUp {
            type boolean;
            config false;
            description "If loop back of the air interface header is currently active (not just configured), this shall be expressed as a 'true'.";
            default false;
        }
        leaf localEndPointId {
            type string;
            config false;
            description "The value of the localEndPointId is a vendor specific identifier of the air interface, used by the node to discover a microwave radio link.";
            default "not-supported";
        }
        leaf remoteEndPointId {
            type string;
            config false;
            description "The value of the remoteEndPointId is a vendor specific identifier or the airinterface at the remote side, used to by the node to discover a microwave radio link.";
            default "not-supported";
        }
    }
    grouping AirInterfaceCurrentProblems {
        list currentProblemList {
            key 'sequenceNumber';
            ordered-by system;
            uses MicrowaveModel-TypeDefinitions:airInterfaceCurrentProblemType;
        }
    }
    grouping AirInterfaceCurrentPerformance {
        description "Aggregated performance information of the air interface at a particular moment.";
        list currentPerformanceDataList {
            description "At least values of the counters, which are reset every 15 minutes, are to be provided. If available, the current values of the counters, which are reset every 24 hour, can be provided, too.";
            key 'scannerId';
            ordered-by system;
            uses MicrowaveModel-TypeDefinitions:airInterfaceCurrentPerformanceType;
            max-elements 2;
            min-elements 1;
        }
    }
    grouping AirInterfaceHistoricalPerformances {
        description "Aggregated performance information of the air interface for a pre-defined measurement interval.";
        list historicalPerformanceDataList {
            key 'historyDataId';
            ordered-by system;
            uses MicrowaveModel-TypeDefinitions:airInterfaceHistoricalPerformanceType;
        }
    }
    list CoChannelGroup {
        description "Required for configuring XPIC, MIMO and ALIC.";
        key 'coChannelGroupId';
        config true;
        leaf coChannelGroupId {
            type CoreModel-CoreFoundationModule-SuperClassesAndCommonPackages:UniversalId;
        }
        leaf-list airInterfaceList {
            description "List of air interfaces, which are part of the co-channel (XPIC, MIMO, ALIC) group.";
            ordered-by system;
            type leafref {
                path '/CoreModel-CoreNetworkModule-ObjectClasses:NetworkElement/CoreModel-CoreNetworkModule-ObjectClasses:_ltpRefList/CoreModel-CoreNetworkModule-ObjectClasses:uuid';
            }
        }
        leaf sortOfCoChannelGroup {
            type string;
            description "Type of group of air interfaces with the same transmit and receive frequency. The values shall be chosen from the following _list:'XPIC', 'MIMO', 'ALIC';";
        }
    }
}
