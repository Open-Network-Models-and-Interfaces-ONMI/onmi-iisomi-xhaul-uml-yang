module eventmanager-api {

    yang-version 1;
    namespace "urn:opendaylight:params:xml:ns:yang:eventmanager:api";
    prefix "eventmanager-api";
    
    import config { prefix config; revision-date 2013-04-05; }
    description
    	"EventManager Api Module";

    revision "2016-03-02" {
        description
            "Initial revision";
    }
    
    identity eventmanager-api {
        base config:service-type;
        config:java-class org.opendaylight.mwtn.eventmanager.api.EventManagerService;
    }
}
