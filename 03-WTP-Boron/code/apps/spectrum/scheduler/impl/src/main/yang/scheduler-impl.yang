module scheduler-impl {
    yang-version 1;
    namespace "urn:opendaylight:params:xml:ns:yang:scheduler:impl";
    prefix "scheduler-impl";

    import config { prefix config; revision-date 2013-04-05; }
    import opendaylight-md-sal-binding { prefix md-sal-binding; revision-date 2013-10-28;}

    description
        "Service definition for scheduler project";

    revision "2014-12-10" {
        description
            "Initial revision";
    }

    identity scheduler {
        base config:module-type;
        config:java-name-prefix Scheduler;
    }

    augment "/config:modules/config:module/config:configuration" {
        case scheduler {
            when "/config:modules/config:module/config:type = 'scheduler'";
            container broker {
                uses config:service-ref {
                    refine type {
                        mandatory true;
                        config:required-identity md-sal-binding:binding-broker-osgi-registry;
                    }
                }
            }
        }
    }
}
