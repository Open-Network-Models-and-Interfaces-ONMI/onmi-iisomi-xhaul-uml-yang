module MicrowaveModel-ObjectClasses-TdmContainer {
    namespace "uri:onf:MicrowaveModel-ObjectClasses-TdmContainer";
    prefix MicrowaveModel-ObjectClasses-TdmContainer;

    import CoreModel-CoreNetworkModule-ObjectClasses {
        prefix CoreModel-CoreNetworkModule-ObjectClasses;
    }
    import MicrowaveModel-TypeDefinitions {
        prefix MicrowaveModel-TypeDefinitions;
    }
    import CoreModel-CoreFoundationModule-TypeDefinitions {
        prefix CoreModel-CoreFoundationModule-TypeDefinitions;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-08-29 {
        description 
            "Initial revision."; 
        reference 
            "ONF TR xyz: A YANG Data Model for Microwave Transport Networks."; 
    }

    feature hybrid-microwave {
        description "Feature 'hybrid-microwave' is mandatory for device types transporting Ethernet + TDM.";
    }
    list MW_TdmContainer_Pac {
        description "LTP(Client)";
        key 'layerProtocol';
        config true;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container tdmContainerCapability {
            config false;
            uses TdmContainerCapability;
        }
        container tdmContainerConfiguration {
            config true;
            uses TdmContainerConfiguration;
        }
        container tdmContainerStatus {
            config false;
            uses TdmContainerStatus;
        }
        container tdmContainerCurrentProblems {
            config false;
            uses TdmContainerCurrentProblems;
        }
        container tdmContainerCurrentPerformance {
            config false;
            uses TdmContainerCurrentPerformance;
        }
        container tdmContainerHistoricalPerformances {
            config false;
            uses TdmContainerHistoricalPerformances;
        }
    }
    grouping TdmContainerCapability {
        description "Bundling is not available.";
        list supportedTdmContainerTypesList {
            description "Lists the TDM containers that are supported.";
            key 'tdmContainerName';
            ordered-by system;
            uses MicrowaveModel-TypeDefinitions:tdmContainerType;
            min-elements 1;
        }
        leaf supportedAlarms {
            type string;
            config false;
            description "Available alarms to be listed. Mandatory:'framingIsFaulty' and 'containerIsDown'. Further alarms might be added by the device.";
            default "Supported alarms not yet defined.";
        }
    }
    grouping TdmContainerConfiguration {
        leaf containerID {
            type string;
            description "ContainterID in Netconf must be the same as EthernetPortID in OpenFlow so a connection can be made between the two items, which separately exist in the controller.";
        }
        container containerType {
            description "Type of TDM container.";
            config true;
            uses MicrowaveModel-TypeDefinitions:tdmContainerType;
        }
        container segmentID {
            description "Multiplicity = 1; One segment per TDM container; Type of segment must match type of container;";
            config true;
            uses MicrowaveModel-TypeDefinitions:segmentIDType;
        }
        list problemSeverityList {
            description "Severity of the problem to be configured.";
            key 'sequenceNumber';
            config false;
            ordered-by system;
            uses MicrowaveModel-TypeDefinitions:containerCurrentProblemType;
            min-elements 2;
        }
    }
    grouping TdmContainerStatus {
        leaf lastStatusChange {
            type CoreModel-CoreFoundationModule-TypeDefinitions:DateAndTime;
            config false;
            description "Time the Container entered its current operational status. 
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
            default "20101120140000.0Z+1";
        }
    }
    grouping TdmContainerCurrentProblems {
        list currentProblemList {
            key 'sequenceNumber';
            ordered-by system;
            uses MicrowaveModel-TypeDefinitions:containerCurrentProblemType;
        }
    }
    grouping TdmContainerCurrentPerformance {
        description "Aggregated performance information of the TDM container at a particular moment.";
        container currentPerformanceData {
            uses MicrowaveModel-TypeDefinitions:containerCurrentPerformanceType;
        }
    }
    grouping TdmContainerHistoricalPerformances {
        description "Aggregated performance information of the TDM container for a pre-defined measurement interval.";
        list historicalPerformanceDataList {
            key 'historyDataId';
            ordered-by system;
            uses MicrowaveModel-TypeDefinitions:containerHistoricalPerformanceType;
        }
    }
}
