module closedLoopAutomation-impl-cfg {
    yang-version 1;
    namespace "urn:opendaylight:params:xml:ns:yang:closedLoopAutomation:impl";
    prefix "cla-impl";

    import config { prefix config; revision-date 2013-04-05; }
    // import closedLoopAutomation-cfg { prefix cfginst; revision-date 2016-09-19; }
    import opendaylight-md-sal-dom {prefix sal; revision-date 2013-10-28; }
    import opendaylight-md-sal-binding { prefix mdsal; revision-date 2013-10-28; }

    organization "Frinx s.r.o";
    contact "Lukas Beles <lbeles@frinx.io>";

    description
        "This module contains the base YANG definitions for the implementation of Closed Loop Automation service.";

    revision "2016-09-29" {
        description
            "Initial revision";
    }

    identity closed-loop-automation-impl {
        base config:module-type;
        config:java-name-prefix ClosedLoopAutomationImpl;
    }

    augment "/config:modules/config:module/config:configuration" {
        case closed-loop-automation-impl {
            when "/config:modules/config:module/config:type = 'closed-loop-automation-impl'";

            container dom-data-provider {
                uses config:service-ref {
                    refine type {
                        mandatory true;
                        config:required-identity sal:dom-async-data-broker;
                    }
                }
            }

            container rpc-registry {
                uses config:service-ref {
                    refine type {
                        mandatory true;
                        config:required-identity mdsal:binding-rpc-registry;
                    }
                }
            }
        }
    }
}
