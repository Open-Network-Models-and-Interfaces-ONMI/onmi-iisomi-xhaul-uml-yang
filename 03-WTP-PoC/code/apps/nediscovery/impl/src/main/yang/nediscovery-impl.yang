/*
 * Copyright (c) 2015 Wipro Ltd. and others.  All rights reserved.
 *
 * This program and the accompanying materials are made available under the
 * terms of the Eclipse Public License v1.0 which accompanies this distribution,
 * and is available at http://www.eclipse.org/legal/epl-v10.html
 */
module nediscovery-impl {
    yang-version 1;
    namespace "urn:opendaylight:params:xml:ns:yang:nediscovery:impl";
    prefix "nediscovery-impl";
	
	import config { prefix config; revision-date 2013-04-05; }
    import opendaylight-md-sal-binding { prefix mdsal; revision-date 2013-10-28;}
    import netconfconnector-api { prefix netconfconnector-api; revision-date 2016-03-02;}
        
    description
    	"Network Element Discovery Impl Module";

    revision "2016-03-02" {
        description
            "Initial revision";
    }

    identity nediscovery-impl {
        base config:module-type;
        config:java-name-prefix NeDiscoveryImpl;
    }

    augment "/config:modules/config:module/config:configuration" {
        case nediscovery-impl {
            when "/config:modules/config:module/config:type = 'nediscovery-impl'";
            container broker {
                uses config:service-ref {
                    refine type {
                        mandatory true;
                        config:required-identity mdsal:binding-broker-osgi-registry;
                    }
                }
            }
            
            container netconfconnector-service {
                uses config:service-ref {
                    refine type {
                        mandatory true;
                        config:required-identity netconfconnector-api:netconfconnector-api;
                    }
                }
            }       
        }
    }
}
