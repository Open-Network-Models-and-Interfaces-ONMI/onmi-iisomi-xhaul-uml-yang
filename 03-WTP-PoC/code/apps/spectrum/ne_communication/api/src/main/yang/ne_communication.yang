module ne_communication {
    yang-version 1;
    namespace "urn:opendaylight:params:xml:ns:yang:ne_communication";
    prefix "ne_communication";

    revision "2015-01-05" {
        description "Initial revision of ne_communication model";
    }
}
