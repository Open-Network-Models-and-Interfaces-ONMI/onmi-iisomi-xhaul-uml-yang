module ne_communication-impl {
    yang-version 1;
    namespace "urn:opendaylight:params:xml:ns:yang:ne_communication:impl";
    prefix "ne_communication-impl";

    import config { prefix config; revision-date 2013-04-05; }
    import opendaylight-md-sal-binding { prefix md-sal-binding; revision-date 2013-10-28;}

    description
        "Service definition for ne_communication project";

    revision "2014-12-10" {
        description
            "Initial revision";
    }

    identity ne_communication {
        base config:module-type;
        config:java-name-prefix Ne_communication;
    }

    augment "/config:modules/config:module/config:configuration" {
        case ne_communication {
            when "/config:modules/config:module/config:type = 'ne_communication'";
            container broker {
                uses config:service-ref {
                    refine type {
                        mandatory true;
                        config:required-identity md-sal-binding:binding-broker-osgi-registry;
                    }
                }
            }
        }
    }
}
