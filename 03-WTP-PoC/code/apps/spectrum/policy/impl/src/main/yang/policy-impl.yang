module policy-impl {
    yang-version 1;
    namespace "urn:opendaylight:params:xml:ns:yang:policy:impl";
    prefix "policy-impl";

    import config { prefix config; revision-date 2013-04-05; }
    import opendaylight-md-sal-binding { prefix md-sal-binding; revision-date 2013-10-28;}

    description
        "Service definition for policy project";

    revision "2014-12-10" {
        description
            "Initial revision";
    }

    identity policy {
        base config:module-type;
        config:java-name-prefix Policy;
    }

    augment "/config:modules/config:module/config:configuration" {
        case policy {
            when "/config:modules/config:module/config:type = 'policy'";
            container broker {
                uses config:service-ref {
                    refine type {
                        mandatory true;
                        config:required-identity md-sal-binding:binding-broker-osgi-registry;
                    }
                }
            }
        }
    }
}
