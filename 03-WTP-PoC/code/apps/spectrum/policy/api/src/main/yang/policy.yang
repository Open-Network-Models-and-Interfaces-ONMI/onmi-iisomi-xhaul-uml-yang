module policy {
    yang-version 1;
    namespace "urn:opendaylight:params:xml:ns:yang:policy";
    prefix "policy";

    revision "2015-01-05" {
        description "Initial revision of policy model";
    }
}
