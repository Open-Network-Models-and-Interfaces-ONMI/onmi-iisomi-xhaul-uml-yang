module neCommunication {
    yang-version 1;
    namespace "urn:opendaylight:params:xml:ns:yang:neCommunication";
    prefix "neCommunication";

    revision "2015-01-05" {
        description "Initial revision of neCommunication model";
    }
}
