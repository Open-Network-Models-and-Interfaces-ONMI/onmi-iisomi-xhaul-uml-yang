module neCommunication-impl {
    yang-version 1;
    namespace "urn:opendaylight:params:xml:ns:yang:neCommunication:impl";
    prefix "neCommunication-impl";

    import config { prefix config; revision-date 2013-04-05; }
    import opendaylight-md-sal-binding { prefix md-sal-binding; revision-date 2013-10-28;}

    description
        "Service definition for neCommunication project";

    revision "2014-12-10" {
        description
            "Initial revision";
    }

    identity neCommunication {
        base config:module-type;
        config:java-name-prefix NeCommunication;
    }

    augment "/config:modules/config:module/config:configuration" {
        case neCommunication {
            when "/config:modules/config:module/config:type = 'neCommunication'";
            container broker {
                uses config:service-ref {
                    refine type {
                        mandatory true;
                        config:required-identity md-sal-binding:binding-broker-osgi-registry;
                    }
                }
            }
        }
    }
}
