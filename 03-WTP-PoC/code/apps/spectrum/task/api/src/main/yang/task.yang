module task {
    yang-version 1;
    namespace "urn:opendaylight:params:xml:ns:yang:task";
    prefix "task";

    revision "2015-01-05" {
        description "Initial revision of task model";
    }
}
