module necommunication {
    yang-version 1;
    namespace "urn:opendaylight:params:xml:ns:yang:necommunication";
    prefix "necommunication";

    revision "2015-01-05" {
        description "Initial revision of necommunication model";
    }
}
