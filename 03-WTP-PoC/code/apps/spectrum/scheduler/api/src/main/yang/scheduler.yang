module scheduler {
    yang-version 1;
    namespace "urn:opendaylight:params:xml:ns:yang:scheduler";
    prefix "scheduler";

    revision "2015-01-05" {
        description "Initial revision of scheduler model";
    }

    rpc next {
    }

}
