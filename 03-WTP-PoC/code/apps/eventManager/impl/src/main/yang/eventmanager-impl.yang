/*
 * Copyright (c) 2015 Wipro Ltd. and others.  All rights reserved.
 *
 * This program and the accompanying materials are made available under the
 * terms of the Eclipse Public License v1.0 which accompanies this distribution,
 * and is available at http://www.eclipse.org/legal/epl-v10.html
 */
module eventmanager-impl {
    yang-version 1;
    namespace "urn:opendaylight:params:xml:ns:yang:eventmanager:impl";
    prefix "eventmanager-impl";
	
	import config { prefix config; revision-date 2013-04-05; }
    import opendaylight-md-sal-binding { prefix mdsal; revision-date 2013-10-28;}
    import eventmanager-api { prefix eventmanager-api; revision-date 2016-03-02;}
    
    description
    	"Event Manager Impl Module";

    revision "2016-03-02" {
        description
            "Initial revision";
    }

    identity eventmanager-impl {
        base config:module-type;
        config:provided-service eventmanager-api:eventmanager-api;
        config:java-name-prefix EventManagerImpl;
    }
    
    augment "/config:modules/config:module/config:configuration" {
        case eventmanager-impl {
            when "/config:modules/config:module/config:type = 'eventmanager-impl'";
            container broker {
                uses config:service-ref {
                    refine type {
                        mandatory true;
                        config:required-identity mdsal:binding-broker-osgi-registry;
                    }
                }
            }
            
            container notification-service {
               uses config:service-ref {
                   refine type {
                       mandatory true;
                       config:required-identity mdsal:binding-notification-service;
                   }
               }
            }
        }
    }
}
