module MicrowaveModel-ObjectClasses-PureEthernetStructure {
    namespace "uri:onf:MicrowaveModel-ObjectClasses-PureEthernetStructure";
    prefix MicrowaveModel-ObjectClasses-PureEthernetStructure;

    import CoreModel-CoreNetworkModule-ObjectClasses {
        prefix CoreModel-CoreNetworkModule-ObjectClasses;
    }
    import CoreModel-CoreFoundationModule-SuperClassesAndCommonPackages {
        prefix CoreModel-CoreFoundationModule-SuperClassesAndCommonPackages;
    }
    import MicrowaveModel-TypeDefinitions {
        prefix MicrowaveModel-TypeDefinitions;
    }
    import CoreModel-CoreFoundationModule-TypeDefinitions {
        prefix CoreModel-CoreFoundationModule-TypeDefinitions;
    }
    import MicrowaveModel-ObjectClasses-SuperClasses {
        prefix MicrowaveModel-ObjectClasses-SuperClasses;
    }
    import G_874_1_model-Object_Classes {
        prefix G_874_1_model-Object_Classes;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-08-09 {
        description 
            "Initial revision."; 
        reference 
            "ONF TR xyz: A YANG Data Model for Microwave Transport Networks."; 
    }

    feature pure-ethernet {
        description "Feature 'pure-ethernet' is mandatory for device types transporting pure Ethernet.";
    }
    list MW_PureEthernetStructure_Pac {
        description "LTP(MWS-TTP)
            The pureEthernetStructure_Pac and its attached classes MUST be provided on management interfaces of microwave devices, which are transporting Ethernet traffic only.";
        key 'layerProtocol';
        config true;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container pureEthernetStructureCapability {
            config false;
            uses PureEthernetStructureCapability;
        }
        container pureEthernetStructureConfiguration {
            config true;
            uses PureEthernetStructureConfiguration;
        }
        container pureEthernetStructureStatus {
            config false;
            uses PureEthernetStructureStatus;
        }
        list pureEthernetStructureCurrentProblemList {
            key 'sequenceNumber';
            config false;
            ordered-by system;
            uses PureEthernetStructureCurrentProblem;
        }
        container pureEthernetStructureCurrentPerformance {
            config false;
            uses PureEthernetStructureCurrentPerformance;
        }
        list pureEthernetStructureHistoricalPerformanceList {
            config false;
            ordered-by system;
            uses PureEthernetStructureHistoricalPerformance;
        }
    }
    grouping PureEthernetStructureCapability {
        description "Describes the logical structuring of the physical capacity provided by a pure Ethernet microwave device.
            Segmentation is not available.
            No fixed segment size.
            No TDM transport.";
        leaf structureId {
            type CoreModel-CoreFoundationModule-SuperClassesAndCommonPackages:UniversalId;
            config false;
            description "Identifies the Structure for bundling and container.";
        }
        leaf supportedAlarms {
            type string;
            config false;
            description "Available alarms to be listed. Mandatory:non. Names are to be separated by commas. Further alarms might be added by the device.";
            default "Supported alarms not yet defined.";
        }
    }
    grouping PureEthernetStructureConfiguration {
        list problemSeverityList {
            description "Severity of the type of problem to be configured.";
            key 'problemId';
            config false;
            ordered-by system;
            uses MicrowaveModel-TypeDefinitions:structureProblemType;
        }
    }
    grouping PureEthernetStructureStatus {
        container segmentStatusList {
            description "Status of the Ethernet transport segment.
                Always just one segment.";
            uses MicrowaveModel-TypeDefinitions:segmentStatusType;
        }
        leaf lastStatusChange {
            type CoreModel-CoreFoundationModule-TypeDefinitions:DateAndTime;
            config false;
            description "Time and date of the last update of the status information.
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
        }
    }
    grouping PureEthernetStructureCurrentProblem {
        uses MicrowaveModel-ObjectClasses-SuperClasses:MwCurrentProblem;
        container problem {
            uses MicrowaveModel-TypeDefinitions:structureProblemType;
        }
    }
    grouping PureEthernetStructureCurrentPerformance {
        uses G_874_1_model-Object_Classes:OTN_CurrentData;
        leaf performanceData {
            type MicrowaveModel-TypeDefinitions:structurePerformanceType;
            config false;
        }
    }
    grouping PureEthernetStructureHistoricalPerformance {
        uses G_874_1_model-Object_Classes:OTN_HistoryData;
        leaf performanceData {
            type MicrowaveModel-TypeDefinitions:structurePerformanceType;
            config false;
        }
    }
}
