module MicrowaveModel-ObjectClasses-HybridMwStructure {
    namespace "uri:onf:MicrowaveModel-ObjectClasses-HybridMwStructure";
    prefix MicrowaveModel-ObjectClasses-HybridMwStructure;

    import CoreModel-CoreNetworkModule-ObjectClasses {
        prefix CoreModel-CoreNetworkModule-ObjectClasses;
    }
    import CoreModel-CoreFoundationModule-SuperClassesAndCommonPackages {
        prefix CoreModel-CoreFoundationModule-SuperClassesAndCommonPackages;
    }
    import MicrowaveModel-TypeDefinitions {
        prefix MicrowaveModel-TypeDefinitions;
    }
    import CoreModel-CoreFoundationModule-TypeDefinitions {
        prefix CoreModel-CoreFoundationModule-TypeDefinitions;
    }
    import MicrowaveModel-ObjectClasses-SuperClasses {
        prefix MicrowaveModel-ObjectClasses-SuperClasses;
    }
    import G_874_1_model-Object_Classes {
        prefix G_874_1_model-Object_Classes;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-07-25 {
        description 
            "Initial revision."; 
        reference 
            "ONF TR xyz: A YANG Data Model for Microwave Transport Networks."; 
    }

    feature hybrid-microwave {
        description "Feature 'hybrid-microwave' is mandatory for device types transporting Ethernet + TDM.";
    }
    list MW_HybridMwStructure_Pac {
        description "LTP(MWS-TTP)";
        key 'layerProtocol';
        config true;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container hybridMwStructureCapability {
            config false;
            uses HybridMwStructureCapability;
        }
        container hybridMwStructureConfiguration {
            config true;
            uses HybridMwStructureConfiguration;
        }
        container hybridMwStructureStatus {
            config false;
            uses HybridMwStructureStatus;
        }
        list hybridMwStructureCurrentProblemList {
            key 'sequenceNumber';
            config false;
            ordered-by system;
            uses HybridMwStructureCurrentProblem;
        }
        container hybridMwStructureCurrentPerformance {
            config false;
            uses HybridMwStructureCurrentPerformance;
        }
        list hybridMwStructureHistoricalPerformanceList {
            config false;
            ordered-by system;
            uses HybridMwStructureHistoricalPerformance;
        }
    }
    grouping HybridMwStructureCapability {
        description "Describes the logical structuring of the physical capacity provided by a hybrid microwave device (TDM + Ethernet).
            Basic principles for defining the Default values of Capability attributes: 1)NO Default values for attributes that MUST be delivered from the device. 2)Default values for every attribute that might be delivered. 3)The Default value shall be inside the value range of the data type of the attribute. 4)The Default value shall be outside the range of reasonable values of the attribute.
            Segmentation is available.
            TDM transport is available.";
        leaf structureId {
            type CoreModel-CoreFoundationModule-SuperClassesAndCommonPackages:UniversalId;
            config false;
            description "Identifies the Structure for bundling and container.";
        }
        list supportedTdmStructureTypesList {
            description "Lists the TDM frames that are supported.";
            key 'tdmStructureTypeId';
            ordered-by system;
            uses MicrowaveModel-TypeDefinitions:tdmStructureType;
            min-elements 1;
        }
        leaf supportedAlarms {
            type string;
            config false;
            description "Available alarms to be listed. Mandatory:non. Names are to be separated by commas. Further alarms might be added by the device.";
            default "Supported alarms not yet defined.";
        }
    }
    grouping HybridMwStructureConfiguration {
        description "Basic principles for defining the Default values of Configuration attributes: 1)NO Default values for attributes that MUST be configured by the controller/operator while starting the device. 2)Default values for every attribute that might be configured also at a later stage. 3)The Default value shall be inside the value range of the data type of the attribute. 4)The Default value shall be outside the range of reasonable values of the attribute. 5)Unless there is a value, which the attribute always has right after starting the device. 6)Configuration messages provided by the device shall contain the current configuration.";
        container structureType {
            description "TDM frame to be applied.";
            config true;
            uses MicrowaveModel-TypeDefinitions:tdmStructureType;
        }
        leaf numberOfTdmSegmentsToBeReserved {
            type int32;
            description "Allows to configure the number of segments reserved for TDM frames of the type specified in HybridMwStructure::HybridMwStructureConfiguration::structureType";
            default -1;
        }
        list problemSeverityList {
            description "Severity of the type of problem to be configured.";
            key 'problemId';
            config false;
            ordered-by system;
            uses MicrowaveModel-TypeDefinitions:structureProblemType;
        }
    }
    grouping HybridMwStructureStatus {
        description "Basic principles for defining the Defaults values of Status attributes: 1)Every attribute shall have a Default value. 2)The Default value shall be inside the value range of the data type of the attribute. 3)The Default value shall be outside the range of reasonable values of the attribute. 4)Unless there is a value, which the attribute always has right after starting the device. 5)Status messages provided by the device shall either contain actual status information or if not possible these default values.";
        list segmentStatusList {
            description "Status of each segment (all TDM and one Ethernet).
                Multiplicity = HybridMwStructure::StructureConfiguration::tdmReservedNumberOfSegments + 1";
            key 'segmentStatusTypeId';
            ordered-by system;
            uses MicrowaveModel-TypeDefinitions:segmentStatusType;
        }
        leaf lastStatusChange {
            type CoreModel-CoreFoundationModule-TypeDefinitions:DateAndTime;
            config false;
            description "Time and date of the last update of the status information.
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
        }
    }
    grouping HybridMwStructureCurrentProblem {
        uses MicrowaveModel-ObjectClasses-SuperClasses:MwCurrentProblem;
        container problem {
            uses MicrowaveModel-TypeDefinitions:structureProblemType;
        }
    }
    grouping HybridMwStructureCurrentPerformance {
        uses G_874_1_model-Object_Classes:OTN_CurrentData;
        leaf performanceData {
            type MicrowaveModel-TypeDefinitions:structurePerformanceType;
            config false;
        }
    }
    grouping HybridMwStructureHistoricalPerformance {
        uses G_874_1_model-Object_Classes:OTN_HistoryData;
        leaf performanceData {
            type MicrowaveModel-TypeDefinitions:structurePerformanceType;
            config false;
        }
    }
}
