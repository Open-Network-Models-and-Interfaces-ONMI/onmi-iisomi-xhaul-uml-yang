module CoreModel-CoreFoundationModule-TypeDefinitions {
    namespace "uri:onf:CoreModel-CoreFoundationModule-TypeDefinitions";
    prefix CoreModel-CoreFoundationModule-TypeDefinitions;
    revision 2016-06-01{}
    typedef DateAndTime {
        description "This primitive type defines the date and time according to the following structure:
            'yyyyMMddhhmmss.s[Z|{+|-}HHMm]' where:
            yyyy    '0000'..'9999'    year
            MM        '01'..'12'            month
            dd        '01'..'31'            day
            hh        '00'..'23'            hour
            mm        '00'..'59'            minute
            ss        '00'..'59'            second
            s        '.0'..'.9'            tenth of second (set to '.0' if EMS or NE cannot support this granularity)
            Z        'Z'                    indicates UTC (rather than local time)
            {+|-}    '+' or '-'            delta from UTC
            HH        '00'..'23'            time zone difference in hours
            Mm        '00'..'59'            time zone difference in minutes.";
        type string;
    }
    typedef BitString {
        description "This primitive type defines a bit oriented string.
            The size of the BitString will be defined in the valueRange property of the attribute; according to ASN.1 (X.680).
            The semantic of each bit position will be defined in the Documentation field of the attribute.";
        type string;
    }
    typedef Real {
        description "This primitive type maps to the 'realnumber' defined in Recommendation X.680.";
        type string;
    }
    typedef PrintableString {
        description "A string that only includes printable characters";
        type string;
    }
}
