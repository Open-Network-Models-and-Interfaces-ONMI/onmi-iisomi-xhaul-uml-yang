module MicrowaveModel-ObjectClasses-AirInterfaceDiversity {
    namespace "uri:onf:MicrowaveModel-ObjectClasses-AirInterfaceDiversity";
    prefix MicrowaveModel-ObjectClasses-AirInterfaceDiversity;

    import CoreModel-CoreNetworkModule-ObjectClasses {
        prefix CoreModel-CoreNetworkModule-ObjectClasses;
    }
    import MicrowaveModel-TypeDefinitions {
        prefix MicrowaveModel-TypeDefinitions;
    }
    import CoreModel-CoreFoundationModule-TypeDefinitions {
        prefix CoreModel-CoreFoundationModule-TypeDefinitions;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-09-01 {
        description 
            "Initial revision."; 
        reference 
            "ONF TR xyz: A YANG Data Model for Microwave Transport Networks."; 
    }

    list MW_AirInterfaceDiversity_Pac {
        description "LTP(MWS-CTP-xD)";
        key 'layerProtocol';
        config true;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container airInterfaceDiversityCapability {
            config false;
            uses AirInterfaceDiversityCapability;
        }
        container airInterfaceDiversityConfiguration {
            config true;
            uses AirInterfaceDiversityConfiguration;
        }
        container airInterfaceDiversityStatus {
            config false;
            uses AirInterfaceDiversityStatus;
        }
        container airInterfaceDiversityCurrentProblems {
            config false;
            uses AirInterfaceDiversityCurrentProblems;
        }
        container airInterfaceDiversityCurrentPerformance {
            config false;
            uses AirInterfaceDiversityCurrentPerformance;
        }
        container airInterfaceDiversityHistoricalPerformances {
            config false;
            uses AirInterfaceDiversityHistoricalPerformances;
        }
    }
    grouping AirInterfaceDiversityCapability {
        description "Describes the capabilities in implementing different types of air interface diversity.";
        list availableKindsOfDiversity {
            description "Available types of diversity to be listed.";
            key 'diversityName';
            ordered-by system;
            uses MicrowaveModel-TypeDefinitions:diversityType;
        }
        leaf supportedAlarms {
            type string;
            config false;
            description "Available alarms to be listed. Mandatory:'airInterfaceDiversityConfigurationIsPartlyDown' (at least one air interface is down, but not all of them) and 'airInterfaceDiversityConfigurationIsDown' (all air interfaces are down). Further alarms might be added by the device. Names are to be separated by commas.";
            default "Supported alarms not yet defined.";
        }
    }
    grouping AirInterfaceDiversityConfiguration {
        container airInterfaceDiversity {
            description "Type of air interface diversity configured at the link.";
            config true;
            uses MicrowaveModel-TypeDefinitions:diversityType;
        }
        leaf-list airInterfaceLtpList {
            description "_multiplicity:2-ThisAirInterfaceDiversity::AirInterfaceDiversityConfiguration::airInterfaceDiversity::diversityType::numberOfAirInterfacesMax";
            ordered-by system;
            type leafref {
                path '/CoreModel-CoreNetworkModule-ObjectClasses:NetworkElement/CoreModel-CoreNetworkModule-ObjectClasses:_ltpRefList/CoreModel-CoreNetworkModule-ObjectClasses:uuid';
            }
            min-elements 2;
        }
        list problemSeverityList {
            description "Severity of the problem to be configured.";
            key 'problemKindName';
            config true;
            ordered-by system;
            uses MicrowaveModel-TypeDefinitions:airInterfaceDiversityProblemSeverityType;
            min-elements 3;
        }
    }
    grouping AirInterfaceDiversityStatus {
        leaf snirCur {
            type int8;
            config false;
            description "Currently measured signal to (noise+interference) ratio of the combined signals.";
            units "dB";
            default -99;
        }
        leaf airInterfaceDiversityStatus {
            type MicrowaveModel-TypeDefinitions:airInterfaceDiversityStatusType;
            config false;
            description "Status of the air interface bundle. ";
            default "groupDown";
        }
        leaf lastStatusChange {
            type CoreModel-CoreFoundationModule-TypeDefinitions:DateAndTime;
            config false;
            description "Time the Diversity Group entered its current operational status. 
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
            default "20101120140000.0Z+1";
        }
    }
    grouping AirInterfaceDiversityCurrentProblems {
        list currentProblemList {
            key 'sequenceNumber';
            ordered-by system;
            uses MicrowaveModel-TypeDefinitions:airInterfaceDiversityCurrentProblemType;
        }
    }
    grouping AirInterfaceDiversityCurrentPerformance {
        description "Aggregated performance information of the air interface diversity configuration at a particular moment.";
        list currentPerformanceDataList {
            description "At least values of the counters, which are reset every 15 minutes, are to be provided. If available, the current values of the counters, which are reset every 24 hour, can be provided, too.";
            key 'scannerId';
            ordered-by system;
            uses MicrowaveModel-TypeDefinitions:airInterfaceDiversityCurrentPerformanceType;
            max-elements 2;
            min-elements 1;
        }
    }
    grouping AirInterfaceDiversityHistoricalPerformances {
        description "Aggregated performance information of the air interface diversity configuration for a pre-defined measurement interval.";
        list historicalPerformanceDataList {
            key 'historyDataId';
            ordered-by system;
            uses MicrowaveModel-TypeDefinitions:airInterfaceDiversityHistoricalPerformanceType;
        }
    }
}
