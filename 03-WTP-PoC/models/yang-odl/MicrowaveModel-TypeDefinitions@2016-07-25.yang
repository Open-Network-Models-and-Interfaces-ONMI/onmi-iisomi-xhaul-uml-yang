module MicrowaveModel-TypeDefinitions {
    namespace "uri:onf:MicrowaveModel-TypeDefinitions";
    prefix MicrowaveModel-TypeDefinitions;

    import CoreModel-CoreFoundationModule-SuperClassesAndCommonPackages {
        prefix CoreModel-CoreFoundationModule-SuperClassesAndCommonPackages;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-07-25 {
        description 
            "Initial revision."; 
        reference 
            "ONF TR xyz: A YANG Data Model for Microwave Transport Networks."; 
    }

    typedef severityType {
        description "According to ITU-T M.3160";
        type enumeration {
            enum non-alarmed;
            enum warning;
            enum minor;
            enum major;
            enum critical;
        }
    }
    grouping channelPlanType {
        leaf channelPlanTypeId {
            type CoreModel-CoreFoundationModule-SuperClassesAndCommonPackages:UniversalId;
            config false;
        }
        leaf supportedChannelPlan {
            type string;
            config false;
            description "Unique name of an international agreement that describe allocations of frequency channels, to which this air interface complies, to be listed. Corresponding channel plans to be delivered by the hardware vendor and to be stored by the operator in the controller/application/attached database.";
            default "Supported Channel Plan not yet defined.";
        }
        leaf duplexDistanceIsVariable {
            type boolean;
            config false;
            description "'1' in case the distance between transmitted and received frequency is variable.";
        }
        leaf duplexDistance {
            type int32;
            config false;
            description "Distance between transmitted and received frequency.";
            units "kHz";
            default -1;
        }
        leaf autoFreqSelectIsAvail {
            type boolean;
            config false;
            description "In case the microwave radio is capable of automatically selecting the transmit frequency in unlicensed bands, this field shall contain an '1'.";
        }
        list transmissionModeList {
            key 'transmissionModeId';
            ordered-by system;
            uses transmissionModeType;
            min-elements 1;
        }
    }
    grouping transmissionModeType {
        description "Basic principles for defining the Default values of Capability/transmissionMode attributes: 1)NO Default values for attributes that MUST be delivered from the device. 2)Default values for every attribute that might be delivered. 3)The Default value shall be inside the value range of the data type of the attribute. 4)The Default value shall be outside the range of reasonable values of the attribute.";
        leaf transmissionModeId {
            type CoreModel-CoreFoundationModule-SuperClassesAndCommonPackages:UniversalId;
            config false;
            description "Indentifies the transmissionMode for internal reference.";
        }
        leaf channelBandwidth {
            type int32;
            config false;
            description "Bandwidth of the transmit channel. The value shall be expressed explicitly (means in kHz) not as a reference to an international agreement. The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;";
            units "kHz";
            default -1;
        }
        leaf modulationScheme {
            type int32;
            config false;
            description "Modulation scheme, which is base to the other characteristics described in the same instance of Script. The modulation scheme shall be described by the number of symbols (e.g. BPSK->'2' or 256QAM->'256').";
            units "symbols";
            default -1;
        }
        leaf informationRate {
            type int32;
            config false;
            description "Information rate of the coding scheme in %.";
            units "%";
            default -1;
        }
        leaf txPowerMin {
            type int32;
            config false;
            description "Value of the minimum transmit power the modem can operate in dBm.";
            units "dBm";
            default 99;
        }
        leaf txPowerMax {
            type int32;
            config false;
            description "Value of the maximum transmit power the modem can operate in dBm.";
            units "dBm";
            default 99;
        }
        leaf rxThreshold {
            type int32;
            config false;
            description "Value of the receive level required to decode the received signal with a Bit Error Rate of 1e-6 or less.";
            units "dBm";
            default 99;
        }
        leaf amUpshiftLevel {
            type int32;
            config false;
            description "Value of the receive level that has to be exceeded to shift into a higher modulation scheme.";
            units "dBm";
            default 99;
        }
        leaf amDownshiftLevel {
            type int32;
            config false;
            description "Value of the receive level that has to be exceeded for not shifting into a lower modulation scheme.";
            units "dBm";
            default 99;
        }
        leaf xpicIsAvail {
            type boolean;
            config false;
            description "In case the Air Interface Port is capable of XPIC, this field shall contain an '1'.";
        }
    }
    typedef polarizationType {
        type enumeration {
            enum horizontal;
            enum vertical;
            enum not-specified;
        }
    }
    grouping airInterfaceProblemType {
        leaf problemId {
            type CoreModel-CoreFoundationModule-SuperClassesAndCommonPackages:UniversalId;
            config false;
        }
        leaf problemName {
            type string;
            config false;
            description "Name of the alarm according to AirInterface::AirInterfaceCapability::supportedAlarms";
            default "Air interface problems not yet defined.";
        }
        leaf problemSeverity {
            type severityType;
            description "Severity of the alarm.";
            default "warning";
        }
    }
    grouping airInterfacePerformanceType {
        description "Consolidated performance information of the air interface.
            Basic principles for defining the Defaults values of Performance attributes: 1)Every attribute shall have a Default value. 2)The Default value shall be inside the value range of the data type of the attribute. 3)The Default value shall be outside the range of reasonable values of the attribute.";
        leaf es {
            type int32;
            config false;
            description "Number of errored seconds.";
            units "s";
            default -1;
        }
        leaf ses {
            type int32;
            config false;
            description "Number of severely errored seconds.";
            units "s";
            default -1;
        }
        leaf cses {
            type int32;
            config false;
            description "Number of consecutive severely errored seconds.";
            units "s";
            default -1;
        }
        leaf unavailability {
            type int32;
            config false;
            description "Total time of unavailability in seconds.";
            units "s";
            default -1;
        }
        leaf txLevelMin {
            type int32;
            config false;
            description "Minimum transmit power. Signed integers are required.";
            units "dBm";
            default 99;
        }
        leaf txLevelMax {
            type int32;
            config false;
            description "Maximum transmit power. Signed integers are required.";
            units "dBm";
            default 99;
        }
        leaf txLevelAvg {
            type int32;
            config false;
            description "Average transmit power. Signed integers are required.";
            units "dBm";
            default 99;
        }
        leaf rxLevelMin {
            type int32;
            config false;
            description "Minimum receive level. Signed integers are required.";
            units "dBm";
            default 99;
        }
        leaf rxLevelMax {
            type int32;
            config false;
            description "Maximum receive level. Signed integers are required.";
            units "dBm";
            default 99;
        }
        leaf rxLevelAvg {
            type int32;
            config false;
            description "Average receive level. Signed integers are required.";
            units "dBm";
            default 99;
        }
        leaf time2Symbols {
            type int32;
            config false;
            units "s";
            default -1;
        }
        leaf time4SymbolsS {
            type int32;
            config false;
            description "Sum of all seconds the transmitter operated in e.g. 4QAM strong.";
            units "s";
            default -1;
        }
        leaf time4Symbols {
            type int32;
            config false;
            units "s";
            default -1;
        }
        leaf time8Symbols {
            type int32;
            config false;
            units "s";
            default -1;
        }
        leaf time16SymbolsS {
            type int32;
            config false;
            units "s";
            default -1;
        }
        leaf time16Symbols {
            type int32;
            config false;
            units "s";
            default -1;
        }
        leaf time32Symbols {
            type int32;
            config false;
            units "s";
            default -1;
        }
        leaf time64Symbols {
            type int32;
            config false;
            units "s";
            default -1;
        }
        leaf time128Symbols {
            type int32;
            config false;
            units "s";
            default -1;
        }
        leaf time256Symbols {
            type int32;
            config false;
            units "s";
            default -1;
        }
        leaf time512Symbols {
            type int32;
            config false;
            units "s";
            default -1;
        }
        leaf time512SymbolsL {
            type int32;
            config false;
            units "s";
            default -1;
        }
        leaf time1024Symbols {
            type int32;
            config false;
            units "s";
            default -1;
        }
        leaf time1024SymbolsL {
            type int32;
            config false;
            units "s";
            default -1;
        }
        leaf time2048Symbols {
            type int32;
            config false;
            units "s";
            default -1;
        }
        leaf time2048SymbolsL {
            type int32;
            config false;
            units "s";
            default -1;
        }
        leaf time4096Symbols {
            type int32;
            config false;
            units "s";
            default -1;
        }
        leaf time4096SymbolsL {
            type int32;
            config false;
            units "s";
            default -1;
        }
        leaf time8192Symbols {
            type int32;
            config false;
            units "s";
            default -1;
        }
        leaf time8192SymbolsL {
            type int32;
            config false;
            units "s";
            default -1;
        }
        leaf snrMin {
            type int32;
            config false;
            description "Minimum signal to noise ratio.";
            units "dB";
            default -99;
        }
        leaf snrMax {
            type int32;
            config false;
            description "Maximum signal to noise ratio.";
            units "dB";
            default -99;
        }
        leaf snrAvg {
            type int32;
            config false;
            description "Average signal to noise ratio.";
            units "dB";
            default -99;
        }
        leaf mseMin {
            type int32;
            config false;
            description "Minimum mean squared error.";
            units "dB";
            default -99;
        }
        leaf mseMax {
            type int32;
            config false;
            description "Maximum mean squared error.";
            units "dB";
            default -99;
        }
        leaf mseAvg {
            type int32;
            config false;
            description "Average mean squared error.";
            units "dB";
            default -99;
        }
        leaf xpdMin {
            type int32;
            config false;
            description "Minimum cross polarization discrimination.";
            units "dB";
            default -99;
        }
        leaf xpdMax {
            type int32;
            config false;
            description "Maximum cross polarization discrimination.";
            units "dB";
            default -99;
        }
        leaf xpdAvg {
            type int32;
            config false;
            description "Average cross polarization discrimination.";
            units "dB";
            default -99;
        }
        leaf rfTempMin {
            type int32;
            config false;
            description "Lowest temperature (in degree Celsius) of the radio module inside the outdoor unit.";
            units "C";
            default -99;
        }
        leaf rfTempMax {
            type int32;
            config false;
            description "Highest temperature (in degree Celsius) of the radio module inside the outdoor unit.";
            units "C";
            default -99;
        }
        leaf rfTempAvg {
            type int32;
            config false;
            description "Average temperature (in degree Celsius) of the radio module inside the outdoor unit.";
            units "C";
            default -99;
        }
        leaf defectBlocksSum {
            type int32;
            config false;
            description "Total number of blocks that were defect after receiving and could not be corrected by the FEC.";
            units "blocks";
            default -1;
        }
        leaf timePeriod {
            type int32;
            config false;
            description "Total length of the measurement period.";
            units "s";
            default -1;
        }
    }
    typedef protectionType {
        type enumeration {
            enum hsb;
        }
    }
    typedef roleType {
        type enumeration {
            enum working;
            enum protection;
            enum protected;
        }
    }
    grouping diversityType {
        leaf diversityTypeId {
            type CoreModel-CoreFoundationModule-SuperClassesAndCommonPackages:UniversalId;
            config false;
        }
        leaf diversityName {
            type string;
            config false;
            description "Names to be chosen from the following list: 'spaceDiversity', 'frequencyDiversity'";
            default "Diversity name not yet defined.";
        }
        leaf numberOfAirInterfacesMax {
            type int32;
            config false;
            description "Maximum number of air interfaces that could be part of this kind of diversity.";
            units "air interfaces";
            default 1;
        }
    }
    typedef airInterfaceDiversityStatusType {
        type enumeration {
            enum allAiActive;
            enum notAllAiActive;
            enum groupDown;
        }
    }
    grouping airInterfaceDiversityProblemType {
        leaf problemId {
            type CoreModel-CoreFoundationModule-SuperClassesAndCommonPackages:UniversalId;
            config false;
        }
        leaf problemName {
            type string;
            config false;
            description "Name of the alarm according to AirInterfaceDiversity::AirInterfaceDiversityCapability::supportedAlarms";
            default "Air interface diversity problems not yet defined.";
        }
        leaf problemSeverity {
            type severityType;
            description "Severity of the alarm.";
            default "warning";
        }
    }
    grouping airInterfaceDiversityPerformanceType {
        description "Consolidated performance information of the air interface diversity group.
            Basic principles for defining the Default values of Performance attributes: 1)Every attribute shall have a Default value. 2)The Default value shall be inside the value range of the data type of the attribute. 3)The Default value shall be outside the range of reasonable values of the attribute.";
        leaf snrMin {
            type int32;
            config false;
            description "Minimum signal to noise ratio of the combined signals.";
            units "dB";
            default -99;
        }
        leaf snrMax {
            type int32;
            config false;
            description "Maximum signal to noise ratio of the combined signals.";
            units "dB";
            default -99;
        }
        leaf snrAvg {
            type int32;
            config false;
            description "Average signal to noise ratio of the combined signals.";
            units "dB";
            default -99;
        }
        leaf mseMin {
            type int32;
            config false;
            description "Minimum mean squared error of the combined signals.";
            units "dB";
            default -99;
        }
        leaf mseMax {
            type int32;
            config false;
            description "Maximum mean squared error of the combined signals.";
            units "dB";
            default -99;
        }
        leaf mseAvg {
            type int32;
            config false;
            description "Average mean squared error of the combined signals.";
            units "dB";
            default -99;
        }
    }
    grouping tdmStructureType {
        leaf tdmStructureTypeId {
            type CoreModel-CoreFoundationModule-SuperClassesAndCommonPackages:UniversalId;
            config false;
        }
        leaf tdmStructureName {
            type string;
            config false;
            description "Names to be chosen from the following list: 'e1','t1','j1','e3','ds3','stm1','cpri1','cpri2','cpri3','cpri4','cpri5','cpri6' or 'cpri7'";
            default "TDM structure name not yet defined.";
        }
        leaf tdmSegmentSize {
            type int32;
            config false;
            description "Size of the TDM segment in kbit/s. Values to be chosen from the following list: '2048','1544','34000','44736 ','155520','614400','1228800','2457600','3072000','4915200','6144000' or '9830400;";
            units "kbit/s";
            default -1;
        }
        leaf maxNumberOfSegmentsReservable {
            type int32;
            config false;
            description "Device specific maximum number of segments (not depending on current air interface configuration) that can be reserved for this type of segment on a single air interface.";
            units "segments";
            default -1;
        }
    }
    grouping structureProblemType {
        leaf problemId {
            type CoreModel-CoreFoundationModule-SuperClassesAndCommonPackages:UniversalId;
            config false;
        }
        leaf problemName {
            type string;
            config false;
            description "Name of the alarm according to Structure::StructureCapability::supportedAlarms";
            default "Structure problems not yet defined.";
        }
        leaf problemSeverity {
            type severityType;
            description "Severity of the alarm.";
            default "warning";
        }
    }
    typedef structurePerformanceType {
        description "Consolidated performance information of the Structure.
            Basic principles for defining the Defaults values of Performance attributes: 1)Every attribute shall have a Default value. 2)The Default value shall be inside the value range of the data type of the attribute. 3)The Default value shall be outside the range of reasonable values of the attribute.";
        type int32;
    }
    grouping tdmContainerType {
        leaf tdmContainerTypeId {
            type CoreModel-CoreFoundationModule-SuperClassesAndCommonPackages:UniversalId;
            config false;
        }
        leaf tdmContainerName {
            type string;
            config false;
            description "Names to be chosen from the following list: 'e1','t1','j1','e3','t3','stm1','cpri1','cpri2','cpri3','cpri4','cpri5','cpri6' or 'cpri7'";
            default "TDM container name not yet defined.";
        }
        leaf tdmContainerSize {
            type int32;
            config false;
            description "Capacity required for transporting this type of container (in kbit/s). Values to be chosen from the following list: '2048','1544','34000','44736 ','155520','614400','1228800','2457600','3072000','4915200','6144000' or '9830400;";
            units "kbit/s";
            default -1;
        }
    }
    grouping segmentIDType {
        description "Identifies the segments, which are used to transport the container.
            Combinations of structureId and segmentId must be unique inside the device to assure that every resource is used just once.";
        leaf structureIdRef {
            type CoreModel-CoreFoundationModule-SuperClassesAndCommonPackages:UniversalId;
        }
        leaf segmentIdRef {
            type int32;
        }
    }
    grouping segmentStatusType {
        leaf segmentStatusTypeId {
            type CoreModel-CoreFoundationModule-SuperClassesAndCommonPackages:UniversalId;
            config false;
        }
        leaf segmentIsReservedForTdm {
            type boolean;
            config false;
            description "The number of segments, which is configured by Structure::StructureConfiguration::tdmReservedNumberOfSegements, has to be reserved for TDM. Starting from the lowest index value, these segments have to be marked with an '1' in segmentIsReservedForTdm.
                ";
        }
    }
    grouping containerProblemType {
        leaf problemId {
            type CoreModel-CoreFoundationModule-SuperClassesAndCommonPackages:UniversalId;
            config false;
        }
        leaf problemName {
            type string;
            config false;
            description "Name of the alarm according to Container::ContainerCapability::supportedAlarms";
            default "Container problems not yet defined.";
        }
        leaf problemSeverity {
            type severityType;
            description "Severity of the alarm.";
            default "warning";
        }
    }
    grouping containerPerformanceType {
        description "Consolidated performance information of the Container.
            Basic principles for defining the Defaults values of Performance attributes: 1)Every attribute shall have a Default value. 2)The Default value shall be inside the value range of the data type of the attribute. 3)The Default value shall be outside the range of reasonable values of the attribute.";
        leaf txEthernetBytesMaxS {
            type int32;
            config false;
            description "Counts the number of Bytes of Ethernet traffic (before header compression) transmitted within a second and keeps the highest value within the measurement period. Field to be left blank for all types of TDM containers.
                Required data volume = 31bit";
            units "Bytes/s";
            default -1;
        }
        leaf txEthernetBytesMaxM {
            type int64;
            config false;
            description "Counts the number of Bytes of Ethernet traffic (before header compression) transmitted within a minute and keeps the highest value with in the measurement period. Field to be left blank for all types of TDM containers.
                Required data volume = 37bit";
            units "Bytes/min";
            default -1;
        }
        leaf txEthernetBytesSum {
            type int64;
            config false;
            description "Total number of Bytes of Ethernet traffic (before header compression) transmitted (in direction out of the device) during the measurement period. Field to be left blank for all types of TDM containers.
                Required data volume = 47bit";
            units "Bytes";
            default -1;
        }
        leaf timePeriod {
            type int32;
            config false;
            description "Total length of the measurement period in seconds.
                Required data volume = 17bit";
            units "s";
            default -1;
        }
    }
}
