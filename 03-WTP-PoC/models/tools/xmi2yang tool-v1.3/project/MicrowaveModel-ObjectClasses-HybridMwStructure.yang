module MicrowaveModel-ObjectClasses-HybridMwStructure {
    namespace "uri:onf:MicrowaveModel-ObjectClasses-HybridMwStructure";
    prefix MicrowaveModel-ObjectClasses-HybridMwStructure;

    import CoreModel-CoreNetworkModule-ObjectClasses {
        prefix CoreModel-CoreNetworkModule-ObjectClasses;
    }
    import CoreModel-CoreFoundationModule-SuperClassesAndCommonPackages {
        prefix CoreModel-CoreFoundationModule-SuperClassesAndCommonPackages;
    }
    import MicrowaveModel-TypeDefinitions {
        prefix MicrowaveModel-TypeDefinitions;
    }
    import CoreModel-CoreFoundationModule-TypeDefinitions {
        prefix CoreModel-CoreFoundationModule-TypeDefinitions;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-09-13 {
        description 
            "Initial revision."; 
        reference 
            "ONF TR 532: A YANG Data Model for Microwave Transport Networks."; 
    }

    feature hybrid-microwave {
        description "Feature 'hybrid-microwave' is mandatory for device types transporting Ethernet + TDM.";
    }
    list MW_HybridMwStructure_Pac {
        description "LTP(MWS-TTP)
            The HybridMwStructure_Pac and its attached classes MUST be provided on management interfaces of microwave devices, which are transporting TDM and Ethernet traffic.";
        key 'layerProtocol';
        config true;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container hybridMwStructureCapability {
            config false;
            uses HybridMwStructureCapability;
        }
        container hybridMwStructureConfiguration {
            config true;
            uses HybridMwStructureConfiguration;
        }
        container hybridMwStructureStatus {
            config false;
            uses HybridMwStructureStatus;
        }
        container hybridMwStructureCurrentProblems {
            config false;
            uses HybridMwStructureCurrentProblems;
        }
        container hybridMwStructureCurrentPerformance {
            config false;
            uses HybridMwStructureCurrentPerformance;
        }
        container hybridMwStructureHistoricalPerformances {
            config false;
            uses HybridMwStructureHistoricalPerformances;
        }
    }
    grouping HybridMwStructureCapability {
        description "Describes the logical structuring of the physical capacity provided by a hybrid microwave device (TDM + Ethernet).
            Segmentation is available.
            TDM transport is available.";
        leaf structureId {
            type CoreModel-CoreFoundationModule-SuperClassesAndCommonPackages:UniversalId;
            config false;
            description "Identifies the Structure for bundling and container.";
        }
        list supportedTdmStructureTypesList {
            description "Lists the TDM frame types that are supported.";
            key 'tdmStructureName';
            ordered-by system;
            uses MicrowaveModel-TypeDefinitions:tdmStructureType;
            min-elements 1;
        }
        leaf supportedAlarms {
            type string;
            config false;
            description "Available alarms to be listed. Mandatory:non. Names are to be separated by commas. Further alarms might be added by the device.";
            default "Supported alarms not yet defined.";
        }
    }
    grouping HybridMwStructureConfiguration {
        container structureType {
            description "TDM frame to be applied.";
            config true;
            uses MicrowaveModel-TypeDefinitions:tdmStructureType;
        }
        leaf numberOfTdmSegmentsToBeReserved {
            type int16;
            description "Allows to configure the number of segments reserved for TDM frames of the type specified in HybridMwStructure::HybridMwStructureConfiguration::structureType";
            default -1;
        }
        list problemKindSeverityList {
            description "Severity of the type of problem to be configured.";
            key 'problemKindName';
            config true;
            ordered-by system;
            uses MicrowaveModel-TypeDefinitions:structureProblemSeverityType;
        }
    }
    grouping HybridMwStructureStatus {
        list segmentStatusList {
            description "Status of each segment (all TDM and one Ethernet).
                Multiplicity = HybridMwStructure::StructureConfiguration::tdmReservedNumberOfSegments + 1";
            key 'segmentStatusTypeId';
            ordered-by system;
            uses MicrowaveModel-TypeDefinitions:segmentStatusType;
        }
        leaf lastStatusChange {
            type CoreModel-CoreFoundationModule-TypeDefinitions:DateAndTime;
            config false;
            description "Time and date of the last update of the status information.
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
        }
    }
    grouping HybridMwStructureCurrentProblems {
        list currentProblemList {
            key 'sequenceNumber';
            ordered-by system;
            uses MicrowaveModel-TypeDefinitions:structureCurrentProblemType;
        }
    }
    grouping HybridMwStructureCurrentPerformance {
        description "Aggregated performance information of the structure of a hybrid microwave at a particular moment.";
        list currentPerformanceDataList {
            description "At least values of the counters, which are reset every 15 minutes, are to be provided. If available, the current values of the counters, which are reset every 24 hour, can be provided, too.";
            key 'scannerId';
            ordered-by system;
            uses MicrowaveModel-TypeDefinitions:structureCurrentPerformanceType;
            max-elements 2;
            min-elements 1;
        }
    }
    grouping HybridMwStructureHistoricalPerformances {
        description "Aggregated performance information of the structure of a hybrid microwave for a pre-defined measurement interval.";
        list historicalPerformanceDataList {
            key 'historyDataId';
            ordered-by system;
            uses MicrowaveModel-TypeDefinitions:structureHistoricalPerformanceType;
        }
    }
}
