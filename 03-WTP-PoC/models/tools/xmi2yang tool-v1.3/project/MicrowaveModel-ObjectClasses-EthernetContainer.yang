module MicrowaveModel-ObjectClasses-EthernetContainer {
    namespace "uri:onf:MicrowaveModel-ObjectClasses-EthernetContainer";
    prefix MicrowaveModel-ObjectClasses-EthernetContainer;

    import CoreModel-CoreNetworkModule-ObjectClasses {
        prefix CoreModel-CoreNetworkModule-ObjectClasses;
    }
    import MicrowaveModel-TypeDefinitions {
        prefix MicrowaveModel-TypeDefinitions;
    }
    import CoreModel-CoreFoundationModule-TypeDefinitions {
        prefix CoreModel-CoreFoundationModule-TypeDefinitions;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-09-02 {
        description 
            "Initial revision."; 
        reference 
            "ONF TR xyz: A YANG Data Model for Microwave Transport Networks."; 
    }

    list MW_EthernetContainer_Pac {
        description "LTP(Client)";
        key 'layerProtocol';
        config true;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "";
        }
        container ethernetContainerCapability {
            config false;
            uses EthernetContainerCapability;
        }
        container ethernetContainerConfiguration {
            config true;
            uses EthernetContainerConfiguration;
        }
        container ethernetContainerStatus {
            config false;
            uses EthernetContainerStatus;
        }
        container ethernetContainerCurrentProblems {
            config false;
            uses EthernetContainerCurrentProblems;
        }
        container ethernetContainerCurrentPerformance {
            config false;
            uses EthernetContainerCurrentPerformance;
        }
        container ethernetContainerHistoricalPerformances {
            config false;
            uses EthernetContainerHistoricalPerformances;
        }
    }
    grouping EthernetContainerCapability {
        leaf bundlingIsAvail {
            type boolean;
            config false;
            description "This attribute has to be set on 'true', if the device allows combining resources from several air interfaces for transporting this Ethernet container.";
            default false;
        }
        leaf packetCompressionIsAvail {
            type boolean;
            config false;
            description "In case packet compression can be activated, but not configured to a certain type, packetCompressionAvail shall be set on 'true', but none of the compression level specific booleans.";
            default false;
        }
        leaf layer2CompressionIsAvail {
            type boolean;
            config false;
            description "Packet compression on layer 2 available at the device.";
            default false;
        }
        leaf vlanCompressionIsAvail {
            type boolean;
            config false;
            description "Packet compression on VLAN layer available at the device.";
            default false;
        }
        leaf qInQCompressionIsAvail {
            type boolean;
            config false;
            description "Packet compression on layer of a second VLAN available at the device.";
            default false;
        }
        leaf mplsCompressionIsAvail {
            type boolean;
            config false;
            description "Packet compression on mpls layer available at the device.";
            default false;
        }
        leaf ipv4CompressionIsAvail {
            type boolean;
            config false;
            description "Packet compression on layer 3 for IPv4 available at the device.";
            default false;
        }
        leaf ipv6CompressionIsAvail {
            type boolean;
            config false;
            description "Packet compression on layer 3 for IPv6 available at the device.";
            default false;
        }
        leaf layer4CompressionIsAvail {
            type boolean;
            config false;
            description "Packet compression on layer 4 (TCP and UDP header) available at the device.";
            default false;
        }
        leaf encryptionIsAvail {
            type boolean;
            config false;
            description "Shall be marked 'true', if Ethernet payload encryption is available.";
            default false;
        }
        leaf supportedAlarms {
            type string;
            config false;
            description "Available alarms to be listed. Mandatory:'framingIsFaulty' and 'containerIsDown'. Further alarms might be added by the device.";
            default "Supported alarms not yet defined.";
        }
    }
    grouping EthernetContainerConfiguration {
        leaf containerID {
            type string;
            description "ContainterID in Netconf must be the same as EthernetPortID in OpenFlow so a connection can be made between the two items, which separately exist in the controller.";
        }
        list segmentsIDList {
            description "Lists the segments used for transporting this Ethernet container. In case EthernetContainer::ContainerCapability::bundlingIsAvail==0, all TypeDefinitions::segmentIdType::structureId must be identical in the list.";
            key 'structureIdRef segmentIdRef';
            config true;
            ordered-by system;
            uses MicrowaveModel-TypeDefinitions:segmentIDType;
            min-elements 1;
        }
        leaf packetCompressionIsOn {
            type boolean;
            description "In case packet compression is activated, but no type is activated, it is assumed that the device chooses the optimum.";
            default false;
        }
        leaf layer2CompressionIsOn {
            type boolean;
            description "Packet compression on layer 2 configured at the device.";
            default false;
        }
        leaf vlanCompressionIsOn {
            type boolean;
            description "Packet compression on VLAN layer configured at the device.";
            default false;
        }
        leaf qInQCompressionIsOn {
            type boolean;
            description "Packet compression on layer of a second VLAN configured at the device.";
            default false;
        }
        leaf mplsCompressionIsOn {
            type boolean;
            description "Packet compression on MPLS layer configured at the device.";
            default false;
        }
        leaf ipv4CompressionIsOn {
            type boolean;
            description "Packet compression on layer 3 for IPv4 configured at the device.";
            default false;
        }
        leaf ipv6CompressionIsOn {
            type boolean;
            description "Packet compression on layer 3 for IPv6 configured at the device.";
            default false;
        }
        leaf layer4CompressionIsOn {
            type boolean;
            description "Packet compression on layer 4 (TCP and UDP header) configured at the device.";
            default false;
        }
        leaf encryptionIsOn {
            type boolean;
            description "Activates encryption of the Ethernet payload.";
            default false;
        }
        leaf cryptographicKey {
            type string;
            description "Key for transforming plaintext into cipher text data.";
            default "Cryptographic key not yet defined.";
        }
        list problemKindSeverityList {
            description "Severity of the problem to be configured.";
            key 'problemKindName';
            config true;
            ordered-by system;
            uses MicrowaveModel-TypeDefinitions:containerProblemSeverityType;
            min-elements 2;
        }
    }
    grouping EthernetContainerStatus {
        leaf lastStatusChange {
            type CoreModel-CoreFoundationModule-TypeDefinitions:DateAndTime;
            config false;
            description "Time the Container entered its current operational status. 
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
            default "20101120140000.0Z+1";
        }
    }
    grouping EthernetContainerCurrentProblems {
        list currentProblemList {
            key 'sequenceNumber';
            ordered-by system;
            uses MicrowaveModel-TypeDefinitions:containerCurrentProblemType;
        }
    }
    grouping EthernetContainerCurrentPerformance {
        description "Aggregated performance information of the Ethernet container at a particular moment.";
        list currentPerformanceDataList {
            key 'scannerId';
            ordered-by system;
            uses MicrowaveModel-TypeDefinitions:containerCurrentPerformanceType;
            max-elements 2;
            min-elements 1;
        }
    }
    grouping EthernetContainerHistoricalPerformances {
        description "Aggregated performance information of the Ethernet container for a pre-defined measurement interval.";
        list historicalPerformanceDataList {
            key 'historyDataId';
            ordered-by system;
            uses MicrowaveModel-TypeDefinitions:containerHistoricalPerformanceType;
        }
    }
}
