module SimpleAirInterface-ObjectClasses {
    namespace "urn:onf:SimpleAirInterface-ObjectClasses";
    prefix SimpleAirInterface-ObjectClasses;
    organization 
        "Open Networking Foundation
         2275 E. Bayshore Road, Suite 103, Palo Alto, CA 94303
         www.opennetworking.org";
    revision 2016-02-22 {
        description
            "generated by xmi2yang";
    }
    container AirInterface {
        config true;
        leaf capAdaptiveModulationIsAvail {
            type boolean;
            config false;
        }
        leaf configAdaptiveModulationIsOn {
            type boolean;
        }
        leaf statusAdaptiveModulationIsOn {
            type boolean;
            config false;
        }
    }
}
