module CoreModel-CoreFoundationModule-TypeDefinitions {
    namespace "urn:onf:CoreModel-CoreFoundationModule-TypeDefinitions";
    prefix CoreModel-CoreFoundationModule-TypeDefinitions;
    organization 
        "Open Networking Foundation
         2275 E. Bayshore Road, Suite 103, Palo Alto, CA 94303
         www.opennetworking.org";
    revision 2016-03-01 {
        description
            "generated by xmi2yang";
    }
    typedef DateAndTime {
        type string;
    }
    typedef BitString {
        type string;
    }
    typedef Real {
        type string;
    }
    typedef PrintableString {
        type string;
    }
}
