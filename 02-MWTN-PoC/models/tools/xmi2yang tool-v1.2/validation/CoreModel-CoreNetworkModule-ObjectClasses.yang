module CoreModel-CoreNetworkModule-ObjectClasses {
    namespace "urn:onf:CoreModel-CoreNetworkModule-ObjectClasses";
    prefix CoreModel-CoreNetworkModule-ObjectClasses;
    import CoreModel-CoreFoundationModule-SuperClassesAndCommonPackages {
        prefix CoreModel-CoreFoundationModule-SuperClassesAndCommonPackages;
    }
    import CoreModel-CoreNetworkModule-TypeDefinitions {
        prefix CoreModel-CoreNetworkModule-TypeDefinitions;
    }
    organization 
        "Open Networking Foundation
         2275 E. Bayshore Road, Suite 103, Palo Alto, CA 94303
         www.opennetworking.org";
    revision 2016-02-28 {
        description
            "generated by xmi2yang";
    }
    list NetworkElement {
        key 'uuid';
        status current;
        config true;
        ordered-by system;
        uses CoreModel-CoreFoundationModule-SuperClassesAndCommonPackages:GlobalClass;
        list ltpRefList {
            description "An NE has associated LTPs that are at its boundary.
                The NeEncompassesFd association occurs for FDs that are within the bounds of the NetworkElement definition such that the FD is bounded by LTPs, all of which are on the boundary of the NetworkElement or are within the NetworkElement. 
                An LTP can be independent of an NE.";
            key 'uuid';
            config true;
            ordered-by system;
            uses LogicalTerminationPoint;
        }
    }
    grouping LayerProtocol {
        uses CoreModel-CoreFoundationModule-SuperClassesAndCommonPackages:LocalClass;
        leaf layerProtocolName {
            type CoreModel-CoreNetworkModule-TypeDefinitions:LayerProtocolName;
            description "Indicate the specific layer-protocol described by the LayerProtocol entity.";
        }
        leaf configuredClientCapacity {
            type string;
            description "Provides a summarized view of the client capacity that is configurable for use.
                Note the cleint LTP association should provide all necessary detail hence this attribute is questionable.";
        }
        leaf lpDirection {
            type CoreModel-CoreNetworkModule-TypeDefinitions:TerminationDirection;
            description "The overall directionality of the LP. 
                - A BIDIRECTIONAL LP will have some SINK and/or SOURCE flowss.
                - A SINK LP can only contain elements with SINK flows or CONTRA_DIRECTION_SOURCE flows
                - A SOURCE LP can only contain SOURCE flows or CONTRA_DIRECTION_SINK flows";
        }
        leaf terminationState {
            type boolean;
            description "Indicates whether the layer is terminated and if so how.";
        }
    }
    grouping LogicalTerminationPoint {
        uses CoreModel-CoreFoundationModule-SuperClassesAndCommonPackages:GlobalClass;
        leaf-list serverLtpRefList {
            description "References contained LTPs representing servers of this LTP in an inverse multiplexing configuration (e.g. VCAT).";
            ordered-by system;
            type leafref {
                path '/NetworkElement/ltpRefList/uuid';
            }
        }
        leaf-list clientLtpRefList {
            description "References contained LTPs representing client traffic of this LTP for normal cases of multiplexing.";
            ordered-by system;
            type leafref {
                path '/NetworkElement/ltpRefList/uuid';
            }
        }
        list lpList {
            description "Ordered list of LayerProtocols that this LTP is comprised of where the first entry in the list is the lowest server layer (e.g. physical)";
            key 'layerProtocolName';
            config true;
            ordered-by system;
            uses LayerProtocol;
            min-elements 1;
        }
        leaf connectedLtpRef {
            type leafref {
                path '/NetworkElement/ltpRefList/uuid';
            }
            description "Applicable in a simple context where two LTPs are associated via a non-adjustable enabled forwarding.
                Reduces clutter removing the need for two additional LTPs and an FC with a pair of FcPorts.";
        }
        leaf peerLtpRef {
            type leafref {
                path '/NetworkElement/ltpRefList/uuid';
            }
            description "References contained LTPs representing the reversal of orientation of flow where two LTPs are associated via a non-adjustable enabled forwarding and where the referenced LTP is fully dependent on the this LTP.";
        }
        leaf-list physicalPortReference {
            description "One or more text labels for the unmodelled physical port associated with the LTP.
                In many cases there is no associated physical port";
            ordered-by system;
            type string;
        }
        leaf-list ltpRefList {
            description "References one or more LTPs in other views that represent this LTP. 
                The referencing LTP is the rovider of capability.";
            ordered-by system;
            type leafref {
                path '/NetworkElement/ltpRefList/uuid';
            }
        }
        leaf ltpDirection {
            type CoreModel-CoreNetworkModule-TypeDefinitions:TerminationDirection;
            description "The overall directionality of the LTP. 
                - A BIDIRECTIONAL LTP must have at least some LPs that are BIDIRECTIONAL but may also have some SINK and/or SOURCE LPs.
                - A SINK LTP can only contain SINK LPs
                - A SOURCE LTP can only contain SOURCE LPs";
        }
    }
}
