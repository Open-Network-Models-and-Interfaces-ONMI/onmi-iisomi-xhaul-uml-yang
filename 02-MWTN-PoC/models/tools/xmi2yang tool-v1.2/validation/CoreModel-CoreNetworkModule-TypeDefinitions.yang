module CoreModel-CoreNetworkModule-TypeDefinitions {
    namespace "urn:onf:CoreModel-CoreNetworkModule-TypeDefinitions";
    prefix CoreModel-CoreNetworkModule-TypeDefinitions;
    organization 
        "Open Networking Foundation
         2275 E. Bayshore Road, Suite 103, Palo Alto, CA 94303
         www.opennetworking.org";
    revision 2016-02-28 {
        description
            "generated by xmi2yang";
    }
    typedef OperType {
        type enumeration {
            enum REVERTIVE;
            enum NON-REVERTIVE;
        }
    }
    typedef LayerProtocolName {
        status current;
        type string;
    }
    typedef PortRole {
        status current;
        type string;
    }
    typedef PortDirection {
        type enumeration {
            enum BIDIRECTIONAL;
            enum INPUT;
            enum OUTPUT;
            enum UNIDENTIFIED_OR_UNKNOWN;
        }
    }
    typedef ForwardingDirection {
        type enumeration {
            enum BIDIRECTIONAL;
            enum UNIDIRECTIONAL;
            enum UNDEFINED_OR_UNKNOWN;
        }
    }
    typedef TerminationDirection {
        type enumeration {
            enum BIDIRECTIONAL;
            enum SINK;
            enum SOURCE;
            enum UNDEFINED_OR_UNKNOWN;
        }
    }
    typedef ExtendedTerminationDirection {
        status current;
        type enumeration {
            enum BIDIRECTIONAL;
            enum SINK;
            enum SOURCE;
            enum UNDEFINED_OR_UNKNOWN;
            enum CONTRA_DIRECTION_SINK;
            enum CONTRA_DIRECTION_SOURCE;
        }
    }
    typedef ProtectionType {
        status current;
        type string;
    }
    typedef TerminationState {
        status current;
        type enumeration {
            enum LP_CAN_NEVER_TERMINATE;
            enum LT_NOT_TERMINATED;
            enum TERMINATED_SERVER_TO_CLIENT_FLOW;
            enum TERMINATED_CLIENT_TO_SERVER_FLOW;
            enum TERMINATED_BIDIRECTIONAL;
            enum LT_PERMENANTLY_TERMINATED;
            enum TERMINATION_STATE_UNKNOWN;
        }
    }
}
