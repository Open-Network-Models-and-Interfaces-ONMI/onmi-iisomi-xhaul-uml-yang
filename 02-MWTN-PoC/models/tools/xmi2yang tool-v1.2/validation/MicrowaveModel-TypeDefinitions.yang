module MicrowaveModel-TypeDefinitions {
    namespace "urn:onf:MicrowaveModel-TypeDefinitions";
    prefix MicrowaveModel-TypeDefinitions;
    import CoreModel-CoreNetworkModule-TypeDefinitions {
        prefix CoreModel-CoreNetworkModule-TypeDefinitions;
    }
    organization 
        "Open Networking Foundation
         2275 E. Bayshore Road, Suite 103, Palo Alto, CA 94303
         www.opennetworking.org";
    revision 2016-03-01 {
        description
            "generated by xmi2yang";
    }
    grouping containerType {
        leaf containerName {
            type string;
            config false;
            description "Names to be chosen from the following list: 'ethernet','e1','t1','j1','e3','ds3','stm1','cpri1','cpri2','cpri3','cpri4','cpri5','cpri6' or 'cpri7'";
        }
        leaf numberOfTimeSlotsRequired {
            type CoreModel-CoreNetworkModule-TypeDefinitions:OperType;
            config false;
            description "Number of time slots required to transport this type of container.";
        }
        leaf bundlingIsAvail {
            type boolean;
            config false;
            description "If it is possible to combine transport resources of several radio links to transport this container type, this attribute shall be set to '1'.";
        }
    }
    typedef diversityType {
        type enumeration {
            enum REVERTIVE;
            enum NON-REVERTIVE;
        }
    }
    typedef severityType {
        type enumeration {
            enum non-alarmed;
            enum warning;
            enum minor;
            enum major;
            enum critical;
        }
    }
    typedef airInterfaceProblemType {
        type string;
    }
    typedef airInterfaceDiversityProblemType {
        type string;
    }
    typedef structureProblemType {
        type string;
    }
    typedef containerProblemType {
        type string;
    }
    container Q_822_numSuppressedIntervalsPkg {
        config true;
        leaf numSuppressedIntervals {
            type uint64;
        }
    }
    container Q_822_historyDataMeasurementListPkg {
        config true;
        leaf cTPId {
            type string;
        }
    }
    container Q_822_historyDataSuspectIntervalFlagPkg {
        config true;
        leaf cTPId {
            type string;
        }
    }
    container Q_822_observedManagedObjectPkg {
        config true;
        leaf observedObjectClass {
            type string;
        }
        leaf observedObjectInstance {
            type string;
        }
    }
    container Q_822_objectDeleteNotificationPkg {
        config true;
        leaf cTPId {
            type string;
        }
    }
}
