module MicrowaveModel-ObjectClasses-MwConnection {
    namespace "urn:onf:MicrowaveModel-ObjectClasses-MwConnection";
    prefix MicrowaveModel-ObjectClasses-MwConnection;
    import CoreModel-CoreNetworkModule-TypeDefinitions {
        prefix CoreModel-CoreNetworkModule-TypeDefinitions;
    }
    import MicrowaveModel-TypeDefinitions {
        prefix MicrowaveModel-TypeDefinitions;
    }
    organization 
        "Open Networking Foundation
         2275 E. Bayshore Road, Suite 103, Palo Alto, CA 94303
         www.opennetworking.org";
    revision 2016-03-01 {
        description
            "generated by xmi2yang";
    }
    grouping MW_AirInterface_Pac {
        list airInterfaceCapabilityList {
            config false;
            ordered-by system;
            uses AirInterfaceCapability;
            min-elements 1;
        }
        container airInterfaceConfiguration {
            config true;
            uses AirInterfaceConfiguration;
        }
        container airInterfaceStatus {
            config false;
            uses AirInterfaceStatus;
        }
        leaf layerProtocol {
            type string;
            config false;
        }
    }
    grouping AirInterfaceCapability {
        status current;
        leaf airInterfaceID {
            type string;
            config false;
            description "Identifies the air interface for connecting with structure or diversity.";
        }
        leaf typeOfEquipment {
            type string;
            config false;
            description "This parameter indicates the equipment type.
Instead of uploading the complete set of capabilities, capabilities of the same equipment type could be reused.";
        }
        leaf supportedChannelPlans {
            type string;
            config false;
            description "Unique identifiers of international agreements that describe allocations of frequency channels, to which this air interface complies, to be listed.
Corresponding channel plans to be delivered by the hardware vendor and to be stored by the operator in the controller/application/attached database.
Names are to be separated by commas.";
        }
        leaf txFrequencyMin {
            type uint64;
            config false;
            description "Value of the minimum transmit frequency tunable at the air interface.
This value is only relevant, if the channel plan, which is referenced in channelPlanID is stored in the controller._unit:kHz";
        }
        leaf txFrequencyMax {
            type uint64;
            config false;
            description "Value of the maximum transmit frequency tunable at the air interface.
This value is only relevant, if the channel plan, which is referenced in channelPlanID is stored in the controller._unit:kHz";
        }
        leaf rxFrequencyMin {
            type uint64;
            config false;
            description "Value of the minimum receive frequency tunable at the air interface.
This value is only relevant, if the channel plan, which is referenced in channelPlanID is stored in the controller._unit:kHz";
        }
        leaf rxFrequencyMax {
            type uint64;
            config false;
            description "Value of the maximum receive frequency tunable at the air interface.
This value is only relevant, if the channel plan, which is referenced in channelPlanID is stored in the controller._unit:kHz";
        }
        leaf adaptiveModulationIsAvail {
            type boolean;
            config false;
            description "In case the Air Interface Port is capable of adaptive modulation, this field shall contain an “1”.";
        }
        list scriptList {
            ordered-by system;
            uses Script;
            min-elements 1;
        }
    }
    grouping Script {
        status current;
        leaf scriptID {
            type string;
            config false;
            description "Indentifies the script for internal reference.";
        }
        leaf channelBandwidth {
            type uint64;
            config false;
            description "Bandwidth of the transmit channel. 
The value shall be expressed explicitly (means in kHz) not as a reference to an international agreement. 
The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;_unit:kHz";
        }
        leaf modulationScheme {
            type CoreModel-CoreNetworkModule-TypeDefinitions:OperType;
            config false;
            description "Modulation scheme, which is base to the other characteristics described in the same instance of Script.
The modulation scheme shall be described by the number of symbols (e.g. BPSK->'2' or 256QAM->'256')._unit:symbols";
        }
        leaf txPowerMin {
            type uint8;
            config false;
            description "Value of the minimum transmit power the modem can operate in dBm._unit:dBm";
        }
        leaf txPowerMax {
            type uint8;
            config false;
            description "Value of the maximum transmit power the modem can operate in dBm._unit:dBm";
        }
        leaf xpicIsAvail {
            type boolean;
            config false;
            description "In case the Air Interface Port is capable of XPIC, this field shall contain an “1”.";
        }
    }
    feature feature1 {
        description "AirInterface::AirInterfaceCapability::adaptiveModulationIsAvail==1";
    }
    feature feature2 {
        description "AirInterface::AirInterfaceCapability::adaptiveModulationIsAvail==1 AND AirInterface::AirInterfaceConfiguration::adaptiveModulationIsOn==1";
    }
    grouping AirInterfaceConfiguration {
        leaf airInterfaceName {
            type string;
            description "Operator specific microwave link ID (often used for coding area, type of element and sequential number).";
        }
        leaf radioSignalId {
            type CoreModel-CoreNetworkModule-TypeDefinitions:OperType;
            description "The radioSignalId is transmitted on the air interface so the remote site of the link synchronizes on the correct transmitter.
The local radio MUST NOT synchronize on a radio signal with a different radioSignalId.
The link ID is neither an ID necessary to span the model nor an ID referencing external data. It is just some sort of name of the link transmitted so the correct remote site can be identified in an interference situation.The value zero might be used to make the microwave to disable the link ID check.";
        }
        leaf txFrequency {
            type uint64;
            description "Center frequency of the transmit channel.
The values to be configured have to exactly match the values listed in the international agreement referenced in channelPlanID.
In case of automated selection of the transmit frequency this field shall describe the lowest center frequency selectable._unit:kHz";
        }
        leaf rxFrequency {
            type uint64;
            description "Center frequency of the receive channel._unit:kHz";
        }
        leaf txChannelBandwidth {
            type uint64;
            description "Bandwidth of the transmit channel. 
The value shall be expressed explicitly (means in kHz) not as a reference to an international agreement. 
The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;_unit:kHz";
        }
        leaf rxChannelBandwidth {
            type uint64;
            description "Bandwidth of the receive channel. 
The value shall be expressed explicitly (means in kHz) not as a reference to an international agreement. 
The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;_unit:kHz";
        }
        leaf powerIsOn {
            type boolean;
            description "Power ON. Activation of the entire radio in a split mount configuration shall be expressed as an “1”.";
        }
        leaf transmitterIsOn {
            type boolean;
            description "Transmit Power. Activation of the transmitter inside the radio shall be expressed as an “1”.";
        }
        leaf txPower {
            type uint8;
            description "Transmit power to be configured on the microwave link. Signed Byte is required.
The actually operated transmit power might be lower depending on adaptive modulation and ATPC._unit:dBm";
        }
        leaf adaptiveModulationIsOn {
            type boolean;
            description "Adaptive Modulation. Activation of adaptive modulation shall be expressed as an “1”.";
            if-feature feature1;
        }
        leaf modulationMin {
            type CoreModel-CoreNetworkModule-TypeDefinitions:OperType;
            description "Minimum modulation to be configured (in case adaptive modulation is not used, this value represents also the fixed modulation).
The modulation scheme shall be described by the number of symbols (e.g. BPSK->'2' or 256QAM->'256').
Allowed values are defined in AirInterface::Script::modulationScheme (all instances of the device)._unit:symbols";
        }
        leaf modulationMax {
            type CoreModel-CoreNetworkModule-TypeDefinitions:OperType;
            description "Maximum modulation to be configured. The value of this field is only relevant, if Adaptive Modulation has been activated.
The modulation scheme shall be described by the number of symbols (e.g. BPSK->'2' or 256QAM->'256').
Allowed values are defined in AirInterface::Script::modulationScheme (all instances of the device)._unit:symbols";
            if-feature feature2;
        }
        leaf xpicIsOn {
            type boolean;
            description "XPIC. Activation of Cross Polarization Interference Cancellation shall be expressed as an “1”.";
        }
    }
    feature feature3 {
        description "(AirInterface::AirInterfaceCapability::autoFreqSelectIsAvail==1 AND AirInterface::AirInterfaceConfiguration::autoFreqSelectIsOn==1 )";
    }
    feature feature4 {
        description "(AirInterface::AirInterfaceCapability::autoFreqSelectIsAvail==1 AND AirInterface::AirInterfaceConfiguration::autoFreqSelectIsOn==1 )";
    }
    feature feature5 {
        description "(AirInterface::AirInterfaceCapability::adaptiveModulationIsAvail AND AirInterface::AirInterfaceConfiguration::adaptiveModulationIsOn) OR (AirInterface::AirInterfaceCapability::atpcIsAvail AND AirInterface::AirInterfaceConfiguration::atpcIsOn)";
    }
    grouping AirInterfaceStatus {
        leaf txFrequencyCur {
            type uint64;
            config false;
            description "Center frequency of the currently operated transmit channel._unit:kHz";
            if-feature feature3;
        }
        leaf rxFrequencyCur {
            type uint64;
            config false;
            description "Center frequency of the currently operated receive channel._unit:kHz";
            if-feature feature4;
        }
        leaf txLevelCur {
            type uint8;
            config false;
            description "Current transmit level. Signed Byte is required._unit:dBm";
            if-feature feature5;
        }
        leaf rxLevelCur {
            type uint8;
            config false;
            description "Current receive level. Signed Byte is required._unit:dBm";
        }
        leaf snrCur {
            type uint8;
            config false;
            description "Currently measured signal to noise ratio._unit:dB";
        }
        leaf linkIsUp {
            type boolean;
            config false;
            description "If connection is established to the remote site with the same linkID, this shall be expressed as an “1”.";
        }
        leaf xpicIsUp {
            type boolean;
            config false;
            description "If XPIC is currently actually working (not just configured), this shall be expressed as an “1”.";
        }
    }
    grouping MW_Structure_Pac {
        container structureCapability {
            config false;
            uses StructureCapability;
        }
        container structureConfiguration {
            config true;
            uses StructureConfiguration;
        }
        container structureStatus {
            config false;
            uses StructureStatus;
        }
        container airInterface_Pac {
            config true;
            uses MW_AirInterface_Pac;
        }
        leaf layerProtocol {
            type string;
            config false;
        }
    }
    grouping StructureCapability {
        status current;
        leaf structureID {
            type string;
            config false;
            description "Identifies the Structure for bundling and container.";
        }
        leaf totalNumberOfTimeSlots {
            type CoreModel-CoreNetworkModule-TypeDefinitions:OperType;
            config false;
            description "Maximum number of time slots available with the current configuration of the air interface (means e.g. that AirInterface::AirInterfaceStatus::modulationCur is equal to AirInterface::AirInterfaceConfiguration::modulationMax).";
        }
    }
    grouping StructureConfiguration {
        leaf serverID {
            type string;
            description "Identifies the physical resource, on which the structure is imprinted on.
Can be filled with either an airInterfaceID, an airInterfaceHsbID or an airInterfaceDiversityID.";
        }
    }
    grouping StructureStatus {
        leaf-list timeSlotStatusList {
            description "Condition of each time slot._multiplicity:Structure::StructureCapability::totalNumberOfTimeSlots";
            ordered-by system;
            type string;
            config false;
        }
    }
    grouping MW_Container_Pac {
        container containerCapability {
            config false;
            uses ContainerCapability;
        }
        container containerConfiguration {
            config true;
            uses ContainerConfiguration;
        }
        container containerStatus {
            config false;
            uses ContainerStatus;
        }
        container mw_structure_pac {
            config true;
            uses MW_Structure_Pac;
        }
        leaf layerProtocol {
            type string;
            config false;
        }
    }
    grouping ContainerCapability {
        status current;
        leaf containerID {
            type string;
            config false;
            description "ContainterID in Netconf must be the same as EthernetPortID in OpenFlow so a connection can be made between the two items, which are existing separately in the controller.";
        }
        list availableKindsOfContainerList {
            description "Available container types to be listed.";
            ordered-by system;
            uses MicrowaveModel-TypeDefinitions:containerType;
            min-elements 1;
        }
    }
    grouping ContainerConfiguration {
        container container {
            description "Defines the data type of the container offered to client layers.";
            config true;
            uses MicrowaveModel-TypeDefinitions:containerType;
        }
        leaf-list timeSlotIDList {
            description "Lists the time slots used for transporting this container.
In case ThisContainer::ContainerConfiguration::container::containerType::bundlingIsAvail==0, structureId must be equal for all aiTimeSlots in the list._multiplicity:ThisContainer::ContainerConfiguration::container::containerType::numberOfTimeSlotsRequired";
            ordered-by system;
            type string;
            min-elements 1;
        }
    }
    grouping ContainerStatus {
    }
}
