module MicrowaveModel-TypeDefinitions {
    namespace "urn:onf:MicrowaveModel-TypeDefinitions";
    prefix MicrowaveModel-TypeDefinitions;
    grouping containerType {
        leaf containerName {
            type string;
            config false;
            description "Names to be chosen from the following list: 'ETHERNET','E1','T1','J1','E3','DS3','STM1','CPRI1','CPRI2','CPRI3','CPRI4','CPRI5','CPRI6' or 'CPRI7'";
        }
        leaf numberOfTimeSlots {
            type uint16;
            config false;
            description "Number of time slots required to transport this type of container.";
        }
        leaf bundlingIsAvail {
            type boolean;
            config false;
            description "Shall be set to '1', if this container type can be transported by timeslots distrubuted over several structures/air interfaces.";
        }
    }
    typedef severityType {
        type enumeration {
            enum non-alarmed;
            enum warning;
            enum minor;
            enum major;
            enum critical;
        }
    }
    grouping airInterfaceProblemType {
        leaf problemName {
            type string;
            config false;
            description "Name of the alarm according to AirInterface::AirInterfaceCapability::supportedAlarms";
        }
        leaf problemSeverity {
            type severityType;
            description "Severity of the alarm.";
        }
    }
    grouping airInterfaceDiversityProblemType {
        leaf problemName {
            type string;
            config false;
            description "Name of the alarm according to AirInterfaceDiversity::AirInterfaceDiversityCapability::supportedAlarms";
        }
        leaf problemSeverity {
            type severityType;
            description "Severity of the alarm.";
        }
    }
    grouping structureProblemType {
        leaf problemName {
            type string;
            config false;
            description "Name of the alarm according to Structure::StructureCapability::supportedAlarms";
        }
        leaf problemSeverity {
            type severityType;
            description "Severity of the alarm.";
        }
    }
    grouping segmentBundlingProblemType {
        leaf problemName {
            type string;
            config false;
            description "Name of the alarm according to SegmentBundling::SegmentBundlingCapability::supportedAlarms";
        }
        leaf problemSeverity {
            type severityType;
            description "Severity of the alarm.";
        }
    }
    grouping containerProblemType {
        leaf problemName {
            type string;
            config false;
            description "Name of the alarm according to Container::ContainerCapability::supportedAlarms";
        }
        leaf problemSeverity {
            type severityType;
            description "Severity of the alarm.";
        }
    }
}
