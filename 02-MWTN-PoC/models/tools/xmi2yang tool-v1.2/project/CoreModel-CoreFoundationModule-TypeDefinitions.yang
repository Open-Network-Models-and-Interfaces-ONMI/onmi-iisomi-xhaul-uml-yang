module CoreModel-CoreFoundationModule-TypeDefinitions {
    namespace "urn:onf:CoreModel-CoreFoundationModule-TypeDefinitions";
    prefix CoreModel-CoreFoundationModule-TypeDefinitions;
    typedef DateAndTime {
        type string;
    }
    typedef BitString {
        type string;
    }
    typedef Real {
        type string;
    }
    typedef PrintableString {
        type string;
    }
}
