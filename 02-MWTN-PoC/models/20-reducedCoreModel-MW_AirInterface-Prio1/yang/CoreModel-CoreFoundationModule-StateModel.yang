module CoreModel-CoreFoundationModule-StateModel {
    namespace "urn:onf:CoreModel-CoreFoundationModule-StateModel";
    prefix CoreModel-CoreFoundationModule-StateModel;
    organization 
        "Open Networking Foundation
         2275 E. Bayshore Road, Suite 103, Palo Alto, CA 94303
         www.opennetworking.org";
    revision 2016-02-24 {
        description
            "generated by xmi2yang";
    }
    grouping State_Pac {
        status current;
        leaf operationalState {
            type OperationalState;
            config false;
            description "The operational state is used to indicate whether or not the resource is installed and working";
        }
        leaf administrativeControl {
            type AdministrativeControl;
            description "The administrativeControl state provides control of the availability of specific resources without modification to the provisioning of those resources.
The value is the current control target. The actual administrativeState may or may not be at target.";
        }
        leaf adminsatratveState {
            type AdministrativeState;
            config false;
            description "Shows whether or not the client has permission to use or has a prohibition against using the resource.
The administrative state expresses usage permissions for specific resources without modification to the provisioning of those resources.";
        }
        leaf lifecycleState {
            type LifecycleState;
            description "Used to track the planned deployment, allocation to clients and withdrawal of resources. ";
        }
    }
    typedef OperationalState {
        status current;
        type enumeration {
            enum DISABLED;
            enum ENABLED;
        }
    }
    typedef AdministrativeState {
        status current;
        type enumeration {
            enum LOCKED;
            enum UNLOCKED;
        }
    }
    typedef AdministrativeControl {
        status deprecated;
        type enumeration {
            enum UNLOCK;
            enum LOCK_PASSIVE;
            enum LOCK_ACTIVE;
            enum LOCK_IMMEDIATE;
        }
    }
    typedef ExtendedAdminState {
        status deprecated;
        type enumeration {
            enum LOCKED;
            enum UNLOCKED;
            enum SHUTTING_DOWN_ACTIVE;
            enum SHUTTING_DOWN_PASSIVE;
        }
    }
    typedef LifecycleState {
        status deprecated;
        type enumeration {
            enum PLANNED;
            enum POTENTIAL;
            enum INSTALLED;
            enum PENDING_REMOVAL;
        }
    }
}
