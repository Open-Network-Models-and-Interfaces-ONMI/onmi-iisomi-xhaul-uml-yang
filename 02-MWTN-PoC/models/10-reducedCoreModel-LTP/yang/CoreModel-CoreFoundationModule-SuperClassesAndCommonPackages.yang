module CoreModel-CoreFoundationModule-SuperClassesAndCommonPackages {
    namespace "urn:onf:CoreModel-CoreFoundationModule-SuperClassesAndCommonPackages";
    prefix CoreModel-CoreFoundationModule-SuperClassesAndCommonPackages;
    import CoreModel-CoreFoundationModule-StateModel {
        prefix CoreModel-CoreFoundationModule-StateModel;
    }
    organization 
        "Open Networking Foundation
         2275 E. Bayshore Road, Suite 103, Palo Alto, CA 94303
         www.opennetworking.org";
    revision 2016-02-22 {
        description
            "generated by xmi2yang";
    }
    grouping Name {
        list nameList {
            description "List of names.";
            key 'valueName';
            config true;
            ordered-by system;
            uses NameAndValue;
            min-elements 1;
        }
    }
    grouping GlobalClass {
        uses Name;
        uses Label;
        uses Extension;
        uses CoreModel-CoreFoundationModule-StateModel:State_Pac;
        list localIdList {
            description "An identifier that is unique in the context of some scope that is less than the global scope.

(consider in the context of Identifier: A property of an entity/role with a value that is unique within an identifier space, where the identifier space is itself unique, and immutable. The identifier therefore represents the identity of the entity/role. An identifier carries no semantics with respect to the purpose of the entity.)";
            key 'valueName';
            config true;
            ordered-by system;
            uses NameAndValue;
        }
        leaf uuid {
            type UniversalId;
            description "UUID: An identifier that is universally unique

(consider in the context of Identifier: A property of an entity/role with a value that is unique within an identifier space, where the identifier space is itself globally unique, and immutable. An identifier carries no semantics with respect to the purpose or state of the entity)";
        }
    }
    grouping LocalClass {
        uses Name;
        uses Label;
        uses Extension;
        uses CoreModel-CoreFoundationModule-StateModel:State_Pac;
        list localIdList {
            description "An identifier that is unique in the context of some scope that is less than the global scope.

(consider in the context of Identifier: A property of an entity/role with a value that is unique within an identifier space, where the identifier space is itself unique, and immutable. The identifier therefore represents the identity of the entity/role. An identifier carries no semantics with respect to the purpose of the entity.)";
            key 'valueName';
            config true;
            ordered-by system;
            uses NameAndValue;
            min-elements 1;
        }
    }
    grouping Label {
        list labelList {
            description "List of labels.";
            key 'valueName';
            config true;
            ordered-by system;
            uses NameAndValue;
        }
    }
    grouping Extension {
        list extensionList {
            description "List of simple name-value extentions";
            key 'valueName';
            config true;
            ordered-by system;
            uses NameAndValue;
        }
    }
    grouping UniversalIdAuthority {
        status current;
        leaf uuid {
            type UniversalId;
            description "The UUID for the UUID authority.";
        }
    }
    grouping NameAndValueAuthority {
        status current;
        leaf uuid {
            type UniversalId;
            description "The UUID for the NameValueAuthority.";
        }
    }
    grouping ConditionalPackage {
        status deprecated;
        uses Extension;
        uses Label;
    }
    grouping NameAndValue {
        leaf valueName {
            type string;
            description "The name of the value. The value need not have a name.";
        }
        leaf value {
            type string;
            description "The value";
        }
        leaf nameAndValueAuthorityRef {
            type string;
            description "The authority that defines the named value.";
        }
        leaf globalClassRef {
            type string;
            description "The scope of the name uniqueness";
        }
        leaf localClassRef {
            type string;
            description "The scope of the name uniqueness";
        }
    }
    typedef UniversalId {
        type string;
    }
}
