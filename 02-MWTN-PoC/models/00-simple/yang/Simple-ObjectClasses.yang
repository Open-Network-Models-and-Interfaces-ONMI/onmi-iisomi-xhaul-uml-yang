module Simple-ObjectClasses {
    namespace "urn:onf:Simple-ObjectClasses";
    prefix Simple-ObjectClasses;
    organization
        "Open Networking Foundation
         2275 E. Bayshore Road, Suite 103, Palo Alto, CA 94303
         www.opennetworking.org";
    revision 2016-02-21 {
        description
            "generated by xmi2yang";
    }
    container TestObject {
        config true;
        leaf uuid {
            type string;
        }
        leaf TestAttribute1 {
            type string;
        }
    }
}
