module MicrowaveModel-Notifications {
    namespace "uri:onf:MicrowaveModel-Notifications";
    prefix MicrowaveModel-Notifications;
    import CoreModel-CoreFoundationModule-TypeDefinitions {
        prefix CoreModel-CoreFoundationModule-TypeDefinitions;
    }
    import CoreModel-CoreFoundationModule-SuperClassesAndCommonPackages {
        prefix CoreModel-CoreFoundationModule-SuperClassesAndCommonPackages;
    }
    revision 2016-03-05 {}
    notification ObjectCreationNotification {
        leaf counter {
            type uint64;
        }
        leaf timeStamp {
            type CoreModel-CoreFoundationModule-TypeDefinitions:DateAndTime;
        }
        leaf objectId {
            type CoreModel-CoreFoundationModule-SuperClassesAndCommonPackages:UniversalId;
        }
    }
    notification ObjectDeletionNotification {
        leaf counter {
            type uint64;
        }
        leaf timeStamp {
            type CoreModel-CoreFoundationModule-TypeDefinitions:DateAndTime;
        }
        leaf objectId {
            type CoreModel-CoreFoundationModule-SuperClassesAndCommonPackages:UniversalId;
        }
    }
    notification AttributeValueChangedNotification {
        leaf counter {
            type uint64;
        }
        leaf timeStamp {
            type CoreModel-CoreFoundationModule-TypeDefinitions:DateAndTime;
        }
        leaf objectId {
            type CoreModel-CoreFoundationModule-SuperClassesAndCommonPackages:UniversalId;
        }
        leaf attributeName {
            type string;
        }
        leaf newValue {
            type string;
            description "Attribute value converted to a sring (xml, json, ...)";
        }
    }
}
