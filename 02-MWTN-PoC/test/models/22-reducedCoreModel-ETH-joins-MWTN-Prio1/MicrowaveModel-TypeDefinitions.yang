module MicrowaveModel-TypeDefinitions {
    namespace "uri:onf:MicrowaveModel-TypeDefinitions";
    prefix MicrowaveModel-TypeDefinitions;
    import CoreModel-CoreFoundationModule-SuperClassesAndCommonPackages {
        prefix CoreModel-CoreFoundationModule-SuperClassesAndCommonPackages;
    }
    import CoreModel-CoreFoundationModule-StateModel {
        prefix CoreModel-CoreFoundationModule-StateModel;
    }
    revision 2016-03-20 {}
    typedef severityType {
        type enumeration {
            enum non-alarmed;
            enum warning;
            enum minor;
            enum major;
            enum critical;
        }
    }
    grouping containerType {
        leaf uuid {
            type CoreModel-CoreFoundationModule-SuperClassesAndCommonPackages:UniversalId;
        }
        leaf containerName {
            type string;
            config false;
            description "Names to be chosen from the following list: 'ethernet','e1','t1','j1','e3','ds3','stm1','cpri1','cpri2','cpri3','cpri4','cpri5','cpri6' or 'cpri7'";
        }
        leaf numberOfTimeSlotsRequired {
            type string;
            config false;
            description "Number of time slots required to transport this type of container.";
        }
        leaf bundlingIsAvail {
            type boolean;
            config false;
            description "If it is possible to combine transport resources of several radio links to transport this container type, this attribute shall be set to '1'.";
        }
    }
    grouping timeSlotIDType {
        leaf structureID {
            type string;
        }
        leaf timeSlotID {
            type string;
        }
    }
    grouping timeSlotStatusType {
        leaf uuid {
            type CoreModel-CoreFoundationModule-SuperClassesAndCommonPackages:UniversalId;
        }
        leaf operationalStatus {
            type CoreModel-CoreFoundationModule-StateModel:OperationalState;
            config false;
            description "Current operational status of each time slot.";
        }
    }
}
