module netconfconnector-api {

    yang-version 1;
    namespace "urn:opendaylight:params:xml:ns:yang:netconfconnector:api";
    prefix "netconfconnector-api";
    
    import config { prefix config; revision-date 2013-04-05; }
    description
    	"NetconfConnector Api Module";

    revision "2016-03-02" {
        description
            "Initial revision";
    }
    
    identity netconfconnector-api {
        base config:service-type;
        config:java-class org.opendaylight.wtg.netconfconnector.api.NetconfConnectorService;
    }
}
