/*
 * Copyright (c) 2015 Wipro Ltd. and others.  All rights reserved.
 *
 * This program and the accompanying materials are made available under the
 * terms of the Eclipse Public License v1.0 which accompanies this distribution,
 * and is available at http://www.eclipse.org/legal/epl-v10.html
 */
module netconfconnector-impl {
    yang-version 1;
    namespace "urn:opendaylight:params:xml:ns:yang:netconfconnector:impl";
    prefix "netconfconnector-impl";
	
	import config { prefix config; revision-date 2013-04-05; }
    import opendaylight-md-sal-binding { prefix mdsal; revision-date 2013-10-28;}
    import netconfconnector-api { prefix netconfconnector-api; revision-date 2016-03-02;}
    import eventmanager-api { prefix eventmanager-api; revision-date 2016-03-02;}
    
    description
    	"Network Connector Impl Module";

    revision "2016-03-02" {
        description
            "Initial revision";
    }

    identity netconfconnector-impl {
        base config:module-type;
        config:provided-service netconfconnector-api:netconfconnector-api;
        config:java-name-prefix NetconfConnectorImpl;
    }
    
    augment "/config:modules/config:module/config:configuration" {
        case netconfconnector-impl {
            when "/config:modules/config:module/config:type = 'netconfconnector-impl'";
            container broker {
                uses config:service-ref {
                    refine type {
                        mandatory true;
                        config:required-identity mdsal:binding-broker-osgi-registry;
                    }
                }
            }
            
            container notification-service {
               uses config:service-ref {
                   refine type {
                       mandatory true;
                       config:required-identity mdsal:binding-notification-service;
                   }
               }
            }
            
            container data-broker {
                uses config:service-ref {
                    refine type {
                        mandatory false;
                        config:required-identity mdsal:binding-async-data-broker;
                    }
                }
            }
            
            container eventmanager-service {
                uses config:service-ref {
                    refine type {
                        mandatory true;
                        config:required-identity eventmanager-api:eventmanager-api;
                    }
                }
            }      
        }
    }
}
