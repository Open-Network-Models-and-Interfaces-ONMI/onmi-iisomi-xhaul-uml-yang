module nediscovery-api {

    yang-version 1;
    namespace "urn:opendaylight:params:xml:ns:yang:nediscovery:api";
    prefix "nediscovery-api";
    
    import NetworkElement { prefix NetworkElement; revision-date 2016-02-03;}
    description
    	"Network Element Discovery Api Module";

    revision "2016-03-02" {
        description
            "Initial revision";
    }
    
    rpc connect {
        description
          "Netconf Server connects to Controller through this rpc";

        input {
            uses NetworkElement:ne;
        }
        output {
            leaf result {
      			description "Result of connect rpc call";
	        	type string;
    		}
        }
    }
    
    rpc disconnect {
        description
          "Netconf Server dis-connects to Controller through this rpc";

        input {
            uses NetworkElement:ne;
        }
        output {
            leaf result {
      			description "Result of disconnect rpc call";
	        	type string;
    		}
        }
    }
}
