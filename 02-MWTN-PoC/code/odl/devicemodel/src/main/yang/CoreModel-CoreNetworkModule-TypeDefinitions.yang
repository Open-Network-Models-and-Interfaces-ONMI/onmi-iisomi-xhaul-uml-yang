module CoreModel-CoreNetworkModule-TypeDefinitions {
    namespace "uri:onf:CoreModel-CoreNetworkModule-TypeDefinitions";
    prefix CoreModel-CoreNetworkModule-TypeDefinitions;
    revision 2016-03-05 {}
    list Q_822_numSuppressedIntervalsPkg {
        key 'numSuppressedIntervals';
        config true;
        leaf numSuppressedIntervals {
            type uint64;
        }
    }
    list Q_822_historyDataMeasurementListPkg {
        key 'cTPId';
        config true;
        leaf cTPId {
            type string;
        }
    }
    list Q_822_historyDataSuspectIntervalFlagPkg {
        key 'cTPId';
        config true;
        leaf cTPId {
            type string;
        }
    }
    list Q_822_observedManagedObjectPkg {
        key 'observedObjectClass';
        config true;
        leaf observedObjectClass {
            type string;
        }
        leaf observedObjectInstance {
            type string;
        }
    }
    list Q_822_objectDeleteNotificationPkg {
        key 'cTPId';
        config true;
        leaf cTPId {
            type string;
        }
    }
    typedef OperType {
        type enumeration {
            enum REVERTIVE;
            enum NON-REVERTIVE;
        }
    }
    typedef LayerProtocolName {
        status current;
        type string;
    }
    typedef PortRole {
        status current;
        type string;
    }
    typedef PortDirection {
        type enumeration {
            enum BIDIRECTIONAL;
            enum INPUT;
            enum OUTPUT;
            enum UNIDENTIFIED_OR_UNKNOWN;
        }
    }
    typedef ForwardingDirection {
        type enumeration {
            enum BIDIRECTIONAL;
            enum UNIDIRECTIONAL;
            enum UNDEFINED_OR_UNKNOWN;
        }
    }
    typedef TerminationDirection {
        type enumeration {
            enum BIDIRECTIONAL;
            enum SINK;
            enum SOURCE;
            enum UNDEFINED_OR_UNKNOWN;
        }
    }
    typedef ExtendedTerminationDirection {
        status current;
        type enumeration {
            enum BIDIRECTIONAL;
            enum SINK;
            enum SOURCE;
            enum UNDEFINED_OR_UNKNOWN;
            enum CONTRA_DIRECTION_SINK;
            enum CONTRA_DIRECTION_SOURCE;
        }
    }
    typedef ProtectionType {
        status current;
        type string;
    }
    typedef TerminationState {
        status current;
        type enumeration {
            enum LP_CAN_NEVER_TERMINATE;
            enum LT_NOT_TERMINATED;
            enum TERMINATED_SERVER_TO_CLIENT_FLOW;
            enum TERMINATED_CLIENT_TO_SERVER_FLOW;
            enum TERMINATED_BIDIRECTIONAL;
            enum LT_PERMENANTLY_TERMINATED;
            enum TERMINATION_STATE_UNKNOWN;
        }
    }
}
