module MicrowaveModel-ObjectClasses-Ethernet {
    namespace "uri:onf:MicrowaveModel-ObjectClasses-Ethernet";
    prefix MicrowaveModel-ObjectClasses-Ethernet;
    import CoreModel-CoreFoundationModule-SuperClassesAndCommonPackages {
        prefix CoreModel-CoreFoundationModule-SuperClassesAndCommonPackages;
    }
    revision 2016-03-20 {}
    list ETH_ConnectionTerminationPointBidirectional_Pac {
        key 'layerProtocol';
        config true;
        description "A very simple ETH-CTP conditional package for microwave device to support an ETH topology. This _Pac is used for 
                     LTPs related to physical ETH ports and MW-Client-CTP.";
        leaf layerProtocol {
            type CoreModel-CoreFoundationModule-SuperClassesAndCommonPackages:UniversalId;
            // type leafref {
            //    path "CoreModel-CoreNetworkModule-ObjectClasses:NetworkElement/_ltpRefList/_lpList/uuid";
            // }
        }
        leaf currentClientCapacity {
            type uint64;
            units "kbit/s";
            config true;
            description "The current transported capacity. The configuredClientCapacity is an existing attribute of the LayerProtocol object class.";
        }
        leaf vlanId {
            type uint64;
            description "Please see ITU-T G.8021 (https://www.itu.int/rec/T-REC-G.8021-201504-I/en).";
        }
        container lldpAlternative {
            uses LldpV2Rem;
            description "An alterantive to LLDP as long as the ETH switches do not support native LLDP (LLDP-V2-MIB).";
        }
    }
  
    grouping LldpV2Rem {
  
        description "A configured alternative for LLDP based on LLDP-V2-MIB (http://www.ieee802.org/1/files/public/MIBs/LLDP-V2-MIB-200906080000Z.txt). 
It is needed in the 2. MWTN PoC because not all vendors will implemented LLDP. 
Therefore the connectivity between LTP-ETH-CTPs needs to be configured according to planning.
Tracy calls it the LLPD of a poor men ;) ";

    leaf lldpV2RemSysName {
        type string;
        description "The string value used to identify the system name of the remote system (NetworkElement::Name).";
    }
    
    leaf lldpV2RemPortId {
        type CoreModel-CoreFoundationModule-SuperClassesAndCommonPackages:UniversalId;
        description "The string value used to identify the port component associated with the remote system. 
In the 2. ONF MWTN PoC the string value of the remote LTP_ETH-CTP::uuid (for remote Microwave device) or a string value for a remote ETH-TTP identifying a host device..";
    }
  }
}
