module MicrowaveModel-ObjectClasses-MwConnection {
    namespace "uri:onf:MicrowaveModel-ObjectClasses-MwConnection";
    prefix MicrowaveModel-ObjectClasses-MwConnection;
    import CoreModel-CoreFoundationModule-SuperClassesAndCommonPackages {
        prefix CoreModel-CoreFoundationModule-SuperClassesAndCommonPackages;
    }
    import MicrowaveModel-TypeDefinitions {
        prefix MicrowaveModel-TypeDefinitions;
    }
    revision 2016-03-23 {}
    list MW_AirInterface_Pac {
        key 'layerProtocol';
        config true;
        leaf layerProtocol {
            type CoreModel-CoreFoundationModule-SuperClassesAndCommonPackages:UniversalId;
            // type leafref {
            //    path "CoreModel-CoreNetworkModule-ObjectClasses:NetworkElement/_ltpRefList/_lpList/uuid";
            // }
            // description "CoreModel-CoreNetworkModule-ObjectClasses:NetworkElement/_ltpRefList/_lpList/uuid";
        }
        list airInterfaceCapabilityList {
            key 'airInterfaceID';
            config false;
            ordered-by system;
            uses AirInterfaceCapability;
            min-elements 1;
        }
        container airInterfaceConfiguration {
            config true;
            uses AirInterfaceConfiguration;
        }
        container airInterfaceStatus {
            config false;
            uses AirInterfaceStatus;
        }
        container airInterfaceCurrentProblemList {
            config false;
            uses AirInterfaceCurrentProblem;
        }
    }
    grouping AirInterfaceCapability {
        status current;
        leaf airInterfaceID {
            type string;
            config false;
            description "Identifies the air interface for connecting with structure or diversity.";
        }
        leaf typeOfEquipment {
            type string;
            config false;
            description "This parameter indicates the equipment type.
Instead of uploading the complete set of capabilities, capabilities of the same equipment type could be reused.";
        }
        leaf supportedChannelPlans {
            type string;
            config false;
            description "Unique identifiers of international agreements that describe allocations of frequency channels, to which this air interface complies, to be listed.
Corresponding channel plans to be delivered by the hardware vendor and to be stored by the operator in the controller/application/attached database.
Names are to be separated by commas.";
        }
        leaf txFrequencyMin {
            type uint64;
            units "kHz";
            config false;
            description "Value of the minimum transmit frequency tunable at the air interface.
This value is only relevant, if the channel plan, which is referenced in channelPlanID is stored in the controller.";
        }
        leaf txFrequencyMax {
            type uint64;
            units "kHz";
            config false;
            description "Value of the maximum transmit frequency tunable at the air interface.
This value is only relevant, if the channel plan, which is referenced in channelPlanID is stored in the controller.";
        }
        leaf rxFrequencyMin {
            type uint64;
            units "kHz";
            config false;
            description "Value of the minimum receive frequency tunable at the air interface.
This value is only relevant, if the channel plan, which is referenced in channelPlanID is stored in the controller.";
        }
        leaf rxFrequencyMax {
            type uint64;
            units "kHz";
            config false;
            description "Value of the maximum receive frequency tunable at the air interface.
This value is only relevant, if the channel plan, which is referenced in channelPlanID is stored in the controller.";
        }
        leaf adaptiveModulationIsAvail {
            type boolean;
            config false;
            description "In case the Air Interface Port is capable of adaptive modulation, this field shall contain an '1'.";
        }
        list scriptList {
            key 'scriptID';
            config false;
            ordered-by system;
            uses Script;
            min-elements 1;
        }
    }
    grouping Script {
        status current;
        leaf scriptID {
            type string;
            config false;
            description "Indentifies the script for internal reference.";
        }
        leaf channelBandwidth {
            type uint64;
            units "kHz";
            config false;
            description "Bandwidth of the transmit channel. 
The value shall be expressed explicitly (means in kHz) not as a reference to an international agreement. 
The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000";
        }
        leaf modulationScheme {
            type uint64;
            units "symbols";
            config false;
            description "Modulation scheme, which is base to the other characteristics described in the same instance of Script.
The modulation scheme shall be described by the number of symbols (e.g. BPSK->'2' or 256QAM->'256').";
        }
        leaf txPowerMin {
            type int64;
            units "dBm";
            config false;
            description "Value of the minimum transmit power the modem can operate in dBm.";
        }
        leaf txPowerMax {
            type int64;
            units "dBm";
            config false;
            description "Value of the maximum transmit power the modem can operate in dBm.";
        }
        leaf xpicIsAvail {
            type boolean;
            config false;
            description "In case the Air Interface Port is capable of XPIC, this field shall contain an '1'.";
        }
    }
    grouping AirInterfaceConfiguration {
        leaf airInterfaceName {
            type string;
            description "Operator specific microwave link ID (often used for coding area, type of element and sequential number).";
        }
        leaf radioSignalId {
            type string;
            description "The radioSignalId is transmitted on the air interface so the remote site of the link synchronizes on the correct transmitter.
The local radio MUST NOT synchronize on a radio signal with a different radioSignalId.
The link ID is neither an ID necessary to span the model nor an ID referencing external data. It is just some sort of name of the link transmitted so the correct remote site can be identified in an interference situation.The value zero might be used to make the microwave to disable the link ID check.";
        }
        leaf txFrequency {
            type uint64;
            units "kHz";
            description "Center frequency of the transmit channel.
The values to be configured have to exactly match the values listed in the international agreement referenced in channelPlanID.
In case of automated selection of the transmit frequency this field shall describe the lowest center frequency selectable.";
        }
        leaf rxFrequency {
            type uint64;
            units "kHz";
            description "Center frequency of the receive channel.";
        }
        leaf txChannelBandwidth {
            type uint64;
            units "kHz";
            description "Bandwidth of the transmit channel. 
The value shall be expressed explicitly (means in kHz) not as a reference to an international agreement. 
The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000";
        }
        leaf rxChannelBandwidth {
            type uint64;
            units "kHz";
            description "Bandwidth of the receive channel. 
The value shall be expressed explicitly (means in kHz) not as a reference to an international agreement. 
The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000";
        }
        leaf powerIsOn {
            type boolean;
            description "Power ON. Activation of the entire radio in a split mount configuration shall be expressed as an '1'.";
        }
        leaf transmitterIsOn {
            type boolean;
            description "Transmit Power. Activation of the transmitter inside the radio shall be expressed as an '1'.";
        }
        leaf txPower {
            type int64;
            units "dBm";
            description "Transmit power to be configured on the microwave link. Signed Byte is required.
The actually operated transmit power might be lower depending on adaptive modulation and ATPC.";
        }
        leaf adaptiveModulationIsOn {
            type boolean;
            description "Adaptive Modulation. Activation of adaptive modulation shall be expressed as an '1'.";
        }
        leaf modulationMin {
            type uint64;
            units "symbols";
            description "Minimum modulation to be configured (in case adaptive modulation is not used, this value represents also the fixed modulation).
The modulation scheme shall be described by the number of symbols (e.g. BPSK->'2' or 256QAM->'256').
Allowed values are defined in AirInterface::Script::modulationScheme (all instances of the device).";
        }
        leaf modulationMax {
            type uint64;
            units "symbols";
            description "Maximum modulation to be configured. The value of this field is only relevant, if Adaptive Modulation has been activated.
The modulation scheme shall be described by the number of symbols (e.g. BPSK->'2' or 256QAM->'256').
Allowed values are defined in AirInterface::Script::modulationScheme (all instances of the device).";
        }
        leaf xpicIsOn {
            type boolean;
            description "XPIC. Activation of Cross Polarization Interference Cancellation shall be expressed as an '1'.";
        }
    }
    grouping AirInterfaceStatus {
        leaf txFrequencyCur {
            type uint64;
            units "kHz";
            config false;
            description "Center frequency of the currently operated transmit channel.";
        }
        leaf rxFrequencyCur {
            type uint64;
            units "kHz";
            config false;
            description "Center frequency of the currently operated receive channel.";
        }
        leaf txLevelCur {
            type int64;
            units "dBm";
            config false;
            description "Current transmit level. Signed Byte is required.";
        }
        leaf rxLevelCur {
            type int64;
            units "dBm";
            config false;
            description "Current receive level. Signed Byte is required.";
        }
        leaf snrCur {
            type int64;
            units "dBm";
            config false;
            description "Currently measured signal to noise ratio.";
        }
        leaf linkIsUp {
            type boolean;
            config false;
            description "If connection is established to the remote site with the same linkID, this shall be expressed as an '1'.";
        }
        leaf xpicIsUp {
            type boolean;
            config false;
            description "If XPIC is currently actually working (not just configured), this shall be expressed as an '1'.";
        }
    }
    grouping AirInterfaceCurrentProblem {
        leaf-list problemList {
            ordered-by system;
            type string;
            config false;
        }
    }
    list MW_Structure_Pac {
        key 'layerProtocol';
        config true;
        leaf layerProtocol {
            type CoreModel-CoreFoundationModule-SuperClassesAndCommonPackages:UniversalId;
            // type leafref {
            //    path "CoreModel-CoreNetworkModule-ObjectClasses:NetworkElement/_ltpRefList/_lpList/uuid";
            // }
            // description "CoreModel-CoreNetworkModule-ObjectClasses:NetworkElement/_ltpRefList/_lpList/uuid";
        }
        container structureCapability {
            config false;
            uses StructureCapability;
        }
        container structureConfiguration {
            config true;
            uses StructureConfiguration;
        }
        container structureStatus {
            config false;
            uses StructureStatus;
        }
    }
    grouping StructureCapability {
        status current;
        leaf structureID {
            type string;
            config false;
            description "Identifies the Structure for bundling and container.";
        }
        leaf totalNumberOfTimeSlots {
            type uint64;
            config false;
            description "Maximum number of time slots available with the current configuration of the air interface (means e.g. that AirInterface::AirInterfaceStatus::modulationCur is equal to AirInterface::AirInterfaceConfiguration::modulationMax).";
        }
        leaf timeSlotCapacity {
            type uint64;
            config false;
            units "kbit/s";
            default 2048;
            description "The value of the size or width of one time slot. The value should be identical for all stuctures of the device.";
        }
    }
    grouping StructureConfiguration {
        leaf serverID {
            type string;
            description "Identifies the physical resource, on which the structure is imprinted on.
Can be filled with either an airInterfaceID, an airInterfaceHsbID or an airInterfaceDiversityID.";
        }
    }
    grouping StructureStatus {
        list timeSlotStatusList {
            key 'structureID timeSlotID';
            config false;
            ordered-by system;
            uses MicrowaveModel-TypeDefinitions:timeSlotStatusType;
            // description "Condition of each timeslot._multiplicity:Structure::StructureCapability::totalNumberOfTimeSlots";
        }
    }
    list MW_Container_Pac {
        key 'layerProtocol';
        config true;
        ordered-by system;
        leaf layerProtocol {
            type CoreModel-CoreFoundationModule-SuperClassesAndCommonPackages:UniversalId;
            // type leafref {
            //    path "CoreModel-CoreNetworkModule-ObjectClasses:NetworkElement/_ltpRefList/_lpList/uuid";
            // }
            // description "CoreModel-CoreNetworkModule-ObjectClasses:NetworkElement/_ltpRefList/_lpList/uuid";
        }
        container containerCapability {
            config false;
            uses ContainerCapability;
        }
        container containerConfiguration {
            config true;
            uses ContainerConfiguration;
        }
        leaf containerStatus {
            type string;
            config false;
        }
    }
    grouping ContainerCapability {
        status current;
        leaf containerID {
            type string;
            config false;
            description "ContainterID in Netconf must be the same as EthernetPortID in OpenFlow so a connection can be made between the two items, which are existing separately in the controller.";
        }
        list availableKindsOfContainerList {
            key 'uuid';
            config false;
            ordered-by system;
            uses MicrowaveModel-TypeDefinitions:containerType;
            min-elements 1;
            description "Available container types to be listed.";
        }
    }
    grouping ContainerConfiguration {
        container container {
            description "Defines the data type of the container offered to client layers.";
            config true;
            uses MicrowaveModel-TypeDefinitions:containerType;
        }
        list timeSlotIDList {
            key 'structureID timeSlotID';
            config true;
            ordered-by system;
            uses MicrowaveModel-TypeDefinitions:timeSlotIDType;
            min-elements 1;
           // description "Lists the time slots used for transporting this container. In case ThisContainer::ContainerConfiguration::container::containerType::bundlingIsAvail==0, structureId must be equal for all aiTimeSlots in the list._multiplicity:ThisContainer::ContainerConfiguration::container::containerType::numberOfTimeSlotsRequired";
        }
    }
}
