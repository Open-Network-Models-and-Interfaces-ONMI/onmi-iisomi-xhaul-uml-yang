module MicrowaveModel-Notifications {
    namespace "uri:onf:MicrowaveModel-Notifications";
    prefix MicrowaveModel-Notifications;
    import CoreModel-CoreFoundationModule-TypeDefinitions {
        prefix CoreModel-CoreFoundationModule-TypeDefinitions;
    }
    import CoreModel-CoreFoundationModule-SuperClassesAndCommonPackages {
        prefix CoreModel-CoreFoundationModule-SuperClassesAndCommonPackages;
    }
    import MicrowaveModel-TypeDefinitions {
        prefix MicrowaveModel-TypeDefinitions;
    }
    revision 2016-03-20 {}
    notification ObjectCreationNotification {
        leaf counter {
            type uint64;
        }
        leaf timeStamp {
            type CoreModel-CoreFoundationModule-TypeDefinitions:DateAndTime;
        }
        leaf objectId {
            type CoreModel-CoreFoundationModule-SuperClassesAndCommonPackages:UniversalId;
        }
    }
    notification ObjectDeletionNotification {
        leaf counter {
            type uint64;
        }
        leaf timeStamp {
            type CoreModel-CoreFoundationModule-TypeDefinitions:DateAndTime;
        }
        leaf objectId {
            type CoreModel-CoreFoundationModule-SuperClassesAndCommonPackages:UniversalId;
        }
    }
    notification AttributeValueChangedNotification {
        leaf counter {
            type uint64;
        }
        leaf timeStamp {
            type CoreModel-CoreFoundationModule-TypeDefinitions:DateAndTime;
        }
        leaf objectId {
            type CoreModel-CoreFoundationModule-SuperClassesAndCommonPackages:UniversalId;
        }
        leaf attributeName {
            type string;
        }
        leaf newValue {
            type string;
            description "Attribute value converted to a sring (xml, json, ...)";
        }
    }
    notification ProblemNotification {
        leaf counter {
            type uint64;
            description "Counts problem notifications";
        }
        leaf timeStamp {
            type CoreModel-CoreFoundationModule-TypeDefinitions:DateAndTime;
        }
        leaf objectID {
            type CoreModel-CoreFoundationModule-SuperClassesAndCommonPackages:UniversalId;
            description "ID of the affected MW_AirInterface_Pac, MW_AirInterfaceDiversity_Pac, MW_Structure_Pac or MW_Container_Pac";
        }
        leaf problem {
            type string;
            description "Name of the problem according to AirInterface::AirInterfaceCapability::supportedAlarms or AirInterfaceDiversity::AirInterfaceDiversityCapability::supportedAlarms or Structure::StructureCapability::supportedAlarms or Container::ContainerCapability::supportedAlarms";
        }
        leaf severity {
            type MicrowaveModel-TypeDefinitions:severityType;
            description "Severity of the problem according to AirInterface::AirInterfaceConfiguration::problemSeverityList, AirInterfaceDiversity::AirInterfaceDiversityConfiguration::problemSeverityList, Structure::StructureConfiguration::problemSeverityList and Container::ContainerConfiguration::problemSeverityList";
        }
    }
}
